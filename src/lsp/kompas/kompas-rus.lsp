(setq *kompas-command-list* '("kompas_in" "kompas_out"))
;;;; (opech_cmds-str *kompas-command-list*)

(defun c:ëùüçôû_øò() (c:kompas_in))
(defun c:ëùüçôû_ùãå() (c:kompas_out))

(princ "Loaded project kompas.\n")
