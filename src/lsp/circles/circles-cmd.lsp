;;;;;;("c_r" "Построение окружности по радиусу и центральной точке." "Отверстия")
(defun c:c_r  (/ p0 p01)
  (princ "\nПостроение окружности по радиусу и центру")
  (setq p0 (getdist "\nРадиус:"))
  (setq p01 (getpoint "\nЦентр:"))
  (command-s "_.circle" p01 p0)
  (princ))

;;;;;;("c_d" "Построение окружности по диаметру и центральной точке." "Отверстия")
(defun c:c_d  (/ p0 p01)
  (princ "\nПостроение окружности по диаметру и центру")
  (setq p0 (* 0.5 (getdist "\nДиаметр:")))
  (setq p01 (getpoint "\nЦентр:"))
  (command-s "_.circle" p01 p0)
  (princ))

;;;;;;("cl_s" "Построение группы окружностей, имеющих один центр." "Отверстия")
(defun c:cl_s  (/ p1 p2 p3 p4 p5 p6 dist ang)
  (princ "\nПостроение окружности по диаметру и центру")
  (setq p1 (getpoint "\nПервая точка на оси:"))
  (setq p2 (getpoint p1 "\nВторая точка на оси:"))
  (setq p3 (getpoint "\nЦентр окружностей:"))
  (setq dist (distance p1 p2))
  (setq ang (angle p1 p2))
  (setq p4 (polar p3 (+ (/ pi 2.) ang) dist))
  (while (setq p5 (getpoint "\nPoint:"))
    (setq p6 (inters p5 (polar p5 ang dist) p3 p4 nil))
    (command-s "_.circle" "_non" p3 "_non" p6))
  (princ))

;;;;;;("ax_c" "Построение окружности с осями." "Отверстия")
(defun c:ax_c  (/ p0 p1 dir_0 r dl alfa)
  (setq p0 (getpoint "\nЦентр окружности:"))
  (setq p1 (getpoint p0 "\nНулевое направление:"))
  (setq dir_0 (angle p0 p1))
  (setq r (getdist "\nРадиус:"))
  (setq dl (getdist "\nРасстояние, на которое оси выходят за пределы окружности:"))
  (setq alfa (getangle "\nУгол поворота осей от нулевого направления:"))
  (axis_ p0 r alfa dl dir_0)
  (command-s "_.circle" "_non" p0 r))

;;;;;;("ax_a" "Построение дуги с осями." "Отверстия")
(defun c:ax_a  (/ p0 p1 dir_0 r dl alfa st_arc vertex_arc)
  (setq p0 (getpoint "\nЦентр дуги:"))
  (setq p1 (getpoint p0 "\nНулевое направление:"))
  (setq dir_0 (angle p0 p1))
  (setq r (getdist "\nРадиус:"))
  (setq dl (getdist "\nРасстояние, на которое оси выходят за пределы окружности:"))
  (setq alfa (getangle "\nУгол поворота осей от нулевого направления:"))
  (setq st_arc (getangle "\nУгол начала дуги:"))
  (setq vertex_arc (getangle "\nУгол конца дуги:"))
  (arc_ p0 r st_arc vertex_arc dir_0)
  (axis_ p0 r alfa dl dir_0))

;;;;;;("ax_ca" "Построение окружности и дуги с осями." "Отверстия")
(defun c:ax_ca  (/ p0 p1 dir_0 ra rc dl alfa st_arc vertex_arc)
  (setq p0 (getpoint "\nЦентр:"))
  (setq p1 (getpoint p0 "\nНулевое направление:"))
  (setq dir_0 (angle p0 p1))
  (setq ra (getdist "\nРадиус дуги:"))
  (setq rc (getdist "\nРадиус окружности:"))
  (setq dl (getdist "\nРасстояние, на которое оси выходят за пределы окружности:"))
  (setq alfa (getangle "\nУгол поворота осей от нулевого направления:"))
  (setq st_arc (getangle "\nУгол начала дуги:"))
  (setq vertex_arc (getangle "\nУгол конца дуги:"))
  (circle_arc p0 rc ra dl alfa st_arc vertex_arc dir_0))

;;;;;;("c_axis" "Построение осей для отмеченных окружностей и дуг." "Отверстия")
(defun c:c_axis  (/ li dl ang num ent_last ent_list ss)
  (princ "\nПроводит оси для отмеченных окружностей и дуг")
  (prompt "\nВыберите окружности или дуги:")
  (setq ent_last (entlast))
  (setq li  (ssget '((-4 . "<OR") (0 . "CIRCLE") (0 . "ARC") (0 . "ELLIPSE") (-4 . "OR>")))
;;;	dl  (getdist "\nРасстояние:")
        dl  0.0
;;;	ang (getangle "\nУгол:")
        ang 0.0)
  (setq li (exclude_small_equal-center_circles (ss_to_list li)))
  (setq num (sslength li))
  (while (>= (setq num (1- num)) 0) (ax (ssname li num) dl ang))
  (setq ent_last (entnext ent_last))
  (while ent_last (setq ent_list (cons ent_last ent_list)) (setq ent_last (entnext ent_last)))
  (setq ss (list_to_ss  ent_list))
  (command-s "select" ss "")
  (princ))

;;;;;;("p_axis" "Построение осей для отмеченных окружностей и дуг." "Отверстия")
(defun c:p_axis  (/ li dl polus num ent_last ent_list ss)
  (princ "\nПроводит оси для отмеченных окружностей и дуг, проходящие через полюс.")
  (prompt "\nВыберите окружности или дуги:")
  (setq ent_last (entlast))
  (setq li    (ssget '((-4 . "<OR") (0 . "CIRCLE") (0 . "ARC") (0 . "ELLIPSE") (-4 . "OR>")))
;;;	dl  (getdist "\nРасстояние:")
        dl    0.0
        polus (getpoint "\nПолюс:"))
  (setq li (exclude_small_equal-center_circles (ss_to_list li)))
  (setq num (sslength li))
  (while (>= (setq num (1- num)) 0) (p_ax (ssname li num) dl polus))
  (setq ent_last (entnext ent_last))
  (while ent_last (setq ent_list (cons ent_last ent_list)) (setq ent_last (entnext ent_last)))
  (setq ss (list_to_ss  ent_list))
  (command-s "select" ss "")
  (princ))

;;;;;;("c_el" "Построение проекции окружности." "Отверстия")
(defun c:c_el  (/ ang p1 p2 p3 p4 pc pe1 pe2)
  (princ "\nПостроение проекции окружности на заданную ось")
  (setq p1  (getpoint "\nВведите первую точку на оси проецирования:")
        p2  (getpoint p1 "\nВведите вторую точку на оси проецирования:")
        p3  (getpoint "\nВведите точку на оси окружности:")
        p4  (getpoint p3 "\nВведите точку на окружности:")
        ang (+ (angle p1 p2) (/ pi 2.))
        pc  (inters p1 p2 p3 (polar p3 ang (distance p1 p2)) nil)
        pe1 (inters p1 p2 p4 (polar p4 ang (distance p1 p2)) nil)
        pe2 (polar pc ang (distance p3 p4)))
  (command-s "_.ellipse" "_c" "_non" pc "_non" pe1 "_non" pe2))

;;;;;;("cl_els" "Построение проекциий окружностей на заданную ось." "Отверстия")
(defun c:cl_els  (/ a_e_pi2 a_c_pi2 p_e1 p_e2 p_c1 p_c2 p0 p1 p2 p3 p4)
  (princ "\nПостроение проекциий окружностей на заданную ось")
  (setq p_e1    (getpoint "\nТочка 1 на оси проецирования:")
        p_e2    (getpoint p_e1 "\nТочка 2 на оси проецирования:")
        a_e_pi2 (+ (angle p_e1 p_e2) (/ pi 2.))
        p_c1    (getpoint "\nТочка 1 на оси окружности:")
        p_c2    (getpoint p_c1 "\nТочка 2 на оси окружности:")
        a_c_pi2 (+ (angle p_c1 p_c2) (/ pi 2.)))
  (while (setq p0 (getpoint "\nВведите точку на окружности:"))
    (setq p1 (inters p_c1 p_c2 p0 (polar p0 a_c_pi2 1.0) nil)
          p2 (inters p_e1 p_e2 p0 (polar p0 a_e_pi2 1.0) nil)
          p3 (inters p_e1 p_e2 p1 (polar p1 a_e_pi2 1.0) nil)
          p4 (polar p3 a_e_pi2 (distance p1 p0)))
    (command-s "_.ellipse" "_c" "_non" p3 "_non" p4 "_non" p2))
  (princ))
