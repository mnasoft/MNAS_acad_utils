(setq *format-command-list* '("format" "make_ublock"))
;;;; (opech_cmds-str *format-command-list*)

(defun c:àùêüôå() (c:format))
(defun c:üôëó_ãèäùñë() (c:make_ublock))

(princ "Loaded project format.\n")
