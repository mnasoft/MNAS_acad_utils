(setq *text-command-list*
       '(;;"mnas-cad-utils-path"
         "pos_export" "de"         "ate"        "t-tr"       "to_15"      "l_text"     "z_text"     "te"
         "stl"        "te+"        "te++"       "te+kvsk"    "te++kvsk"   "te-"        "te-kvsk"    "te%%c"
         "te-%%c"     "x45%%d"     "&a&b&c"     "te_*"       "te_<>_"     "text_export"             "attrnorm"
         "textnorm"   "textnorms"  "tn"         "tns"        "tmatchprop" "tma"        "test_err" "tcopy" "tcp"))
;;;; (opech_cmds-str *text-command-list*)

(defun c:зщы_учзщке () (c:pos_export))
(defun c:ву () (c:de))
(defun c:феу () (c:ate))
(defun c:е-ек () (c:t-tr))
(defun c:ещ_15 () (c:to_15))
(defun c:д_еуче () (c:l_text))
(defun c:я_еуче () (c:z_text))
(defun c:еу () (c:te))
(defun c:ыед () (c:stl))
(defun c:еу+ () (c:te+))
(defun c:еу++ () (c:te++))
(defun c:еу+лмыл () (c:te+kvsk))
(defun c:еу++лмыл () (c:te++kvsk))
(defun c:еу- () (c:te-))
(defun c:еу-лмыл () (c:te-kvsk))
(defun c:еу%%с () (c:te%%c))
(defun c:еу-%%с () (c:te-%%c))
(defun c:ч45%%в () (c:x45%%d))
(defun c:&ф&и&с () (c:&a&b&c))
(defun c:еу_* () (c:te_*))
(defun c:еу_БЮ_ () (c:te_<>_))
(defun c:еуче_учзщке () (c:text_export))
(defun c:феектщкь () (c:attrnorm))
(defun c:еучетщкь () (c:textnorm))
(defun c:еучетщкьы () (c:textnorms))
(defun c:ет () (c:tn))
(defun c:еты () (c:tns))
(defun c:еьфесрзкщз () (c:tmatchprop))
(defun c:еьф () (c:tma))
(defun c:еуые_укк () (c:test_err))
(defun c:есщзн() (c:tcopy))
(defun c:есз() (c:tcp))

(princ "Loaded project text.\n")
