(setq *clock-command-list* '("clock_off" "clock_on"))
;;;; (opech_cmds-str *clock-command-list*)

(defun c:ñäùñë_ùàà() (c:clock_off))
(defun c:ñäùñë_ùò() (c:clock_on))

(princ "Loaded project clock.\n")
