(defun c:ctr()
  (setq r (getdist "\nВведите радиус:"))
  (setq pnt (getpoint "\nВведите точку:" ))
  (setq ed_line (CAR(entsel "\nУкажите линию:")))
  (entmake (list
	     (cons 0 "CIRCLE")
	     (cons 10 pnt)
	     (cons 40 r)
	   )
  )
  (command-s "_offset" r ed_line pnt "_exit")
)
;(entmake (list	     (cons 0 "LINE")	     (cons 10 pnt)	     (cons 11 (list 0 0 0))	   )  )
