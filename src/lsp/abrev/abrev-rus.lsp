(setq *abbrev-command-list*
       '("pur" "sk" "tm" "za" "zc" "zd"	"ze" "zp" "zv" "zw" "fr" "chd" "git" "vl" "vu" "lou" "gr_on_off" "xa" "lim"))

;;;'("ra" "rg"   "rga"  "vs"   "z"	   "f"	  "ch"	 "s"	"l"    "a"    "o"    "c"    "e"	   "co"	  "cp"	 "m"	"ro"
;;;       "tr"   "ex"   "rec"  "mi"   "el"	  "br"	 "u"	"undo" "sc"   "oops" "di"   "id"   "ma"	  "le"	 "op"	"h"
;;;       "dt"   "pe"   "bo"   "ar"   "li"	  "x"	 "j"	"b"    "ps"   "ms")

;;;;(opech_cmds-str *abbrev-command-list*)

(defun c:згк() (c:pur))
(defun c:ыл() (c:sk))
(defun c:еь() (c:tm))
(defun c:яф() (c:za))
(defun c:яс() (c:zc))
(defun c:яв() (c:zd))
(defun c:яу() (c:ze))
(defun c:яз() (c:zp))
(defun c:ям() (c:zv))
(defun c:яц() (c:zw))
(defun c:ак() (c:fr))
(defun c:срв() (c:chd))
(defun c:пше() (c:git))
(defun c:мд() (c:vl))
(defun c:мг() (c:vu))
(defun c:дщг() (c:lou))
(defun c:пк_щт_щаа() (c:gr_on_off))
(defun c:чф() (c:xa))
(defun c:дшь() (c:lim))

;;;(defun c:кф () (c:ra))
;;;(defun c:кп () (c:rg))
;;;(defun c:кпф () (c:rga))
;;;(defun c:мы () (c:vs))
;;;(defun c:я () (c:z))
;;;(defun c:а () (c:f))
;;;(defun c:ср () (c:ch))
;;;(defun c:ы () (c:s))
;;;(defun c:д () (c:l))
;;;(defun c:ф () (c:a))
;;;(defun c:щ () (c:o))
;;;(defun c:с () (c:c))
;;;(defun c:у () (c:e))
;;;(defun c:сщ () (c:co))
;;;(defun c:сз () (c:cp))
;;;(defun c:ь () (c:m))
;;;(defun c:кщ () (c:ro))
;;;(defun c:ек () (c:tr))
;;;(defun c:уч () (c:ex))
;;;(defun c:кус () (c:rec))
;;;(defun c:ьш () (c:mi))
;;;(defun c:уд () (c:el))
;;;(defun c:ик () (c:br))
;;;(defun c:г () (c:u))
;;;(defun c:гтвщ () (c:undo))
;;;(defun c:ыс () (c:sc))
;;;(defun c:щщзы () (c:oops))
;;;(defun c:вш () (c:di))
;;;(defun c:шв () (c:id))
;;;(defun c:ьф () (c:ma))
;;;(defun c:ду () (c:le))
;;;(defun c:щз () (c:op))
;;;(defun c:р () (c:h))
;;;(defun c:ве () (c:dt))
;;;(defun c:зу () (c:pe))
;;;(defun c:ищ () (c:bo))
;;;(defun c:фк () (c:ar))
;;;(defun c:дш () (c:li))
;;;(defun c:ч () (c:x))
;;;(defun c:о () (c:j))
;;;(defun c:и () (c:b))
;;;(defun c:зы () (c:ps))
;;;(defun c:ьы () (c:ms))

(princ "Loaded project abrev.\n")
