;;;;;;("ren"
;;;;;;"Транслитерация имен слоев и стилей на английский алфавит." "not defined")
(defun c:ren  (/ la)
  (princ "Переименование имен слоев и стилей под английский алфавит.")
  (err-init '("cmdecho"))
  (set-sys-var-lst '(("cmdecho" 0)))
  (mapcar (function (lambda (el) (tbles el 2))) (list "LAYER" "LTYPE" "VIEW" "STYLE" "BLOCK"))
  (err-handle ""))

(defun tbles  (tbl_name code / tbl)
  (setq tbl (tblnext tbl_name t))
  (if tbl
    (ren_tbl tbl code))
  (while (setq tbl (tblnext tbl_name)) (ren_tbl tbl code)))

(defun ren_tbl  (tbl code)
  (setq name     (strcase (cdr (assoc code tbl)))
        new_name (ch_name name)
        tblname  (strcase (cdr (assoc 0 tbl))))
  (if (/= name new_name)
    (progn (print (strcat tblname " = " name " -> " new_name))
           (command-s "_.rename" (strcat "_" tblname) name new_name))))

(defun ch_name  (name / l n4)
  (setq n4 "")
  (while (>= (strlen name) 1)
    (setq n1   name
          name (substr name 2))
    (dos_dos n1 'n4))
  (eval n4))

(defun dos_dos  (n1 n2 / n3 no)
  (setq no (substr n1 1 1))
  (setq n3 (cond ((= no "А") "A")
                 ((= no "Б") "B")
                 ((= no "В") "V")
                 ((= no "Г") "G")
                 ((= no "Д") "D")
                 ((= no "Е") "E")
                 ((= no "Ё") "E")
                 ((= no "Ж") "G")
                 ((= no "З") "Z")
                 ((= no "И") "I")
                 ((= no "Й") "J")
                 ((= no "К") "K")
                 ((= no "Л") "L")
                 ((= no "М") "M")
                 ((= no "Н") "N")
                 ((= no "О") "O")
                 ((= no "П") "P")
                 ((= no "Р") "R")
                 ((= no "С") "S")
                 ((= no "Т") "T")
                 ((= no "У") "U")
                 ((= no "Ф") "PH")
                 ((= no "Х") "H")
                 ((= no "Ц") "CZ")
                 ((= no "Ч") "CH")
                 ((= no "Х") "H")
                 ((= no "Ш") "SH")
                 ((= no "Щ") "SCH")
                 ((= no "Ь") "")
                 ((= no "Ы") "Y")
                 ((= no "Ъ") "")
                 ((= no "Э") "AE")
                 ((= no "Ю") "JU")
                 ((= no "Я") "JA")
                 (t no)))
  (set n2 (strcat (eval n2) n3)))
