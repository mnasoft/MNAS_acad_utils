"Òàáëèöà Á.1 – Îñíîâíûå ïàðàìåòðû ÃÒÄ ÄÌ80Ë ¹1 ïðè ðàáîòå íà äèçåëüíîì òîïëèâå â áîêñå 10 öåõà 100"
(setq *tbl-b1* '(("Äàòà"	"-"	                "11.08.17" "04.08.17" "04.08.17" "04.08.17" "04.08.17" "11.08.17" "11.08.17" "14.08.17")
		 ("Âðåìÿ"	"-"	                "15:59:14" "15:26:43" "15:47:01" "16:17:18" "16:45:21" "16:35:52" "16:55:54" "16:24:19")
		 ("Ne, ÌÂò"	"GQ010"	                0.00	0.98	4.02	7.99	10.98	13.97	16.82	18.03)
		 ("nÊÂÄ, îá/ìèí"	"EN2"	        7361	7620	8250	8716	8893	9055	9247	9242)
		 ("nÊÍÄ, îá/ìèí"	"EN1"	        4650	5208	6295	7122	6949	6952	7018	7066)
		 ("t04, °C"	"T04"	                419.6	467.4	581.0	676.3	701.9	734.4	783.4	775.9)
		 ("dt04max, °C"	"dT04plus"	        7.5	10.9	17.1	28.5	25.3	25.8	24.1	28.6)
		 ("dt04min, °C"	"dT04minus"	        -9.2	-9.1	-13.9	-19.0	-12.4	-14.3	-16.1	-17.5)
		 ("tÍÂ, °C"	"T01"	                38.7	41.6	44.8	43.8	45.4	42.9	44.9	34.5)
		 ("p2, êÏà"	"P02"	                450.1	538.0	764.9	1014.0	1187.6	1358.2	1493.6	1565.1)
		 ("tÄÒ, °C"	"FT020"	                35.3	35.2	36.4	37.4	37.8	36.8	36.8	24.9)
		 ("GÊÄÒ1, êã/÷"	"G2"	                795.2	1059.0	1906.0	2931.0	3422.0	4047.0	4659.0	4946.0)
		 ("pÄÒ1, êÏà"	"FP240"	                598.9	771	1286	2008	2544	3202	3884	4197)
		 ("KÄÒ, %"	"FA020"	                14.36	18.46	25.84	37.06	41.67	48.91	54.31	57.55)
		 ("ÊÄÒ.Ð, %"	"FA026"	                14.57	18.87	26.16	37.49	42.14	49.36	54.77	57.96)
		 ("tÃÒ, °C"	"FT010"	                38.5	44.2	47.9	50.0	50.0	48.9	50.0	38.2)
		 ("GÊÃÒ3, êã/÷"	"G1"	                0.00	0.11	0.11	0.11	0.11	0.00	0.00	0.11)
		 ("PÊÃÒ3, Ïà"	"FP040"	                0.0	3.4	4.3	0.3	0.0	0.0	0.0	0.0)
		 ("KÃÒ, %"	"FA010"	                0.1	0.2	0.2	0.2	0.2	0.1	0.1	0.1)
		 ("ÊÃÒ.Ð, %"	"FA016"	                0.0	0.0	0.0	0.0	0.0	0.0	0.0	0.0)
		 ("nÊÌ, îá/ìèí"	"RN110"	                17086	14985	14980	13980	13974	13492	13490	13522)
		 ("VÊÌ.Ã, ìì/ñ"	"RB220"	                7.5	2.4	2.4	2.4	2.6	2.2	2.4	1.8)
		 ("VÊÌ.Î, ìì/ñ"	"RB230"	                7.0	6.5	5.9	2.4	2.5	1.1	1.7	0.9)
		 ("tÊÌ.ÏÎÄØ.1, °C"	"RT210"	        56.5	52.8	55.7	53.0	46.5	55.6	58.1	44.9)
		 ("tÊÌ.ÏÎÄØ.2, °C"	"RT220"	        60.7	55.1	58.6	56.5	55.0	59.2	62.8	45.7)
		 ("tÊÌ.ÂÕ.1, °C"	"PT030"	        46.9	50.5	55.8	50.2	53.1	50.1	54.1	58.2)
		 ("tÊÌ.ÂÕ.2, °C"	"PT031"	        47.5	48.9	54.2	50.2	53.7	49.9	53.9	57.2)
		 ("tÊÌ.ÂÛÕ.1, °C"	"PT040"	        65.1	49.5	50.8	60.2	63.8	64.3	68.7	82.7)
		 ("tÊÌ.ÂÛÕ.2, °C"	"PT041"	        63.4	49.9	52.1	60.3	63.2	65.1	68.9	88.0)
		 ("dPÑ.GÂ.ÊÌ, Ïà"	"PP081"	        796.9	158.7	166.3	184.0	191.4	891.9	189.3	3000.8)
		 ("GÂ.ÊÌ, ã/c"	"PQ020"	                560.8	135.1	159.8	192.0	209.4	964.8	463.2	924.7)
		 ("GÂ.ÊÌ.ÏÐ, ã/ñ"	"PQ020_pr"	108.7	22.6	19.9	18.5	17.5	70.9	31.3	61.7)
		 ("tÊÌ.ÎÁ.ÑÒ, °C"	"RT100"	        110.30	104.70	112.60	110.30	117.90	122.80	124.50	140.30)
		 ("KSAM, %"	"PA010"	                40.08	40.01	40.15	40.18	40.34	35.37	35.40	50.20)
		 ("KSAM_Ó, %"	"PA016"	                40.00	40.00	40.00	40.00	40.00	35.00	35.00	50.00)
		 ("tÂ.ÊÑ.ÂÛÕ, °C"	"PT010"	        257.5	282.2	348.2	400.0	400.0	400.0	400.0	400.0)
		 ("tÂ.ÂÎ.ÂÕ, °C"	"PT020"	        164.8	180.6	219.8	254.3	262.1	294.9	318.5	220.9)
		 ("dP2-ÊÄÒ1, êÏà"	"FP470"	        84.1	98.1	98.1	98.1	98.1	98.1	98.1	98.1)
		 ("dP2-ÊÂ2, êÏà"	"FP450"	        44.8	37.9	50.9	57.1	65.9	69.6	72.5	56.0)
		 ("dP2-ÊÃÒ3, êÏà"	"FP460"	        11.0	0.0	0.0	0.0	0.0	16.5	16.8	15.9)
		 ("tÂ.ÊÂ2, °C"	"PT050"	                40.3	42.0	44.0	46.7	47.9	43.6	45.4	37.8)
		 ("tÂ.ÊÄÒ1, °C"	"PT060"	                52.8	63.9	74.5	78.9	81.1	71.0	79.1	59.3)
		 ("tÂ.ÊÃÒ3, °C"	"PT070"	                61.8	62.8	69.4	64.7	65.4	64.7	66.4	64.8)
		 ("PÂ.ÊÂ2, êÏà"	"PP040"	                503.5	589.1	831.0	1071.9	1251.3	1430.8	1563.2	1627.9)
		 ("PÂ.ÊÄÒ1, êÏà"	"PP050"	        470.4	455.0	430.8	475.4	489.7	481.0	498.6	455.5)
		 ("PÂ.ÊÃÒ3, êÏà"	"PP060"	        482.2	568.6	800.8	1052.3	1229.8	1398.4	1533.8	1598.5)
		 ("PÂ.ÂÎ.ÂÕ, êÏà"	"PP070"	        459.3	547.4	771.9	1018.9	1190.5	1360.2	1490.6	1525.9)
		 ("GÂ.ÔÎÐÑ, ã/ñ"	"PQ010"	        0.00	0.00	0.00	0.00	0.00	0.00	0.00	0.25)
		 ("ÏÊÑ.1, êÏà"	"-"	                0.9	"-"	1.5	1.4	1.8	1.8	2.1	"-")
		 ("ÏÊÑ.2, êÏà"	"-"	                0.9	"-"	1.3	1.3	1.8	1.8	2.0	"-")
		 ("ÏÊÑ.3, êÏà"	"-"	                1.4	"-"	1.6	1.8	2.2	2.2	2.6	"-")
		 ("f, Ãö"	"-"	                129	"-"	239	"øóì"	364	364	265	"-")
		 ("EMNOx,15,dry, ìã/íì3 15 % Î2"	"-"	300	281	287	342	395	520	658	"-")
		 ("EMCO,15,dry, ìã/íì3 15 % Î2"	"-"	143	63	9	3	4	5	7	"-")
		 ("ôÎ2,dry, % îá."	"-"	        18.41	18.01	17.08	16.37	16.13	15.83	15.45	"-")
		 ("NeÊÌ, %"	"-"	                "-"	25	32	36	41	""	""	"-"))) 

"Òàáëèöà Á.2 – Îñíîâíûå ïàðàìåòðû ÃÒÄ ÄÌ80Ë ¹1 ïðè ðàáîòå íà ãàçîîáðàçíîì òîïëèâå â áîêñå 10 öåõà 100"
(setq *tbl-b2* '(("Äàòà"	"-"	"21.08.17" "21.08.17" "21.08.17" "21.08.17" "21.08.17" "21.08.17" "21.08.17" "21.08.17")
		("Âðåìÿ"	"-"	"11:09:06" "11:28:30" "11:47:30" "11:47:30" "12:18:08" "12:33:31" "12:53:40" "16:19:48")
		("Ne, ÌÂò"	"GQ010"	                0.00	1.00	4.00	8.02	11.00	13.99	16.52	16.49)
		("nÊÂÄ, îá/ìèí"	"EN2"	                6101	7575	8200	8659	8829	9053	9221	9248)
		("nÊÍÄ, îá/ìèí"	"EN1"	                2992	5199	6270	7032	6882	6910	7000	7018)
		("t04, °C"	"T04"	                369.9	451.2	559.7	643.9	673.0	719.5	762.8	768.6)
		("dt04max, °C"	"dT04plus"	        15.2	18.5	21.7	23.9	24.0	24.2	22.4	22.0)
		("dt04min, °C"	"dT04minus"	        11.2	11.5	14.6	14.8	9.5	10.4	15.7	16.1)
		("tÍÂ, °C"	"T01"	                32.2	35.7	38.6	37.0	38.7	40.6	42.7	45.6)
		("p2, êÏà"	"P02"	                207.1	543.4	768.3	1025.8	1197.4	1355.3	1475.9	1469.0)
		("tÄÒ, °C"	"FT020"	                25.3	25.8	26.4	26.7	27.2	27.6	28.3	31.9)
		("GÊÄÒ1, êã/÷"	"G2"	                0	0	0	0	0	0	0	0)
		("pÄÒ1, êÏà"	"FP240"	                29.3	32.6	37.1	43.5	46.3	47.1	48.9	50.9)
		("KÄÒ, %"	"FA020"	                0	0	0	0	0	0	0	0)
		("ÊÄÒ.Ð, %"	"FA026"	                0	0	0	0	0	0	0	0)
		("tÃÒ, °C"	"FT010"	                35.3	37.8	38.2	37.5	35.6	34.4	33.2	28.01)
		("GÊÃÒ3, êã/÷"	"G1"	                600	1261	1898	2683	3110	3516	3943	3952)
		("PÊÃÒ3, Ïà"	"FP040"	                227.8	624.3	924.7	1270.9	1503.4	1757.4	1930.9	1918.2)
		("KÃÒ, %"	"FA010"	                10.78	18.83	26.86	38.51	48.34	63.54	99.95	87.92)
		("ÊÃÒ.Ð, %"	"FA016"	                10.55	18.56	26.46	38.02	48.02	63.46	100	87.85)
		("nÊÌ, îá/ìèí"	"RN110"	                16980	15042	15032	13970	13990	13475	13478	13487)
		("VÊÌ.Ã, ìì/ñ"	"RB220"	                7.6	3.2	2.5	2.4	2.1	1.9	1.9	2.2)
		("VÊÌ.Î, ìì/ñ"	"RB230"	                5.8	3.5	5.5	2.3	2.3	1.1	1.2	1.4)
		("tÊÌ.ÏÎÄØ.1, °C"	"RT210"	        53.4	55.5	57.0	54.0	42.2	44.4	45.4	54.4)
		("tÊÌ.ÏÎÄØ.2, °C"	"RT220"	        56.8	58.0	60.2	56.9	51.0	52.9	56.7	58.7)
		("tÊÌ.ÂÕ.1, °C"	"PT030"	                34.7	43.9	48.5	42.7	45.1	48.8	52.0	55.4)
		("tÊÌ.ÂÕ.2, °C"	"PT031"	                35.1	47.0	51.5	41.3	45.0	48.5	52.2	52.9)
		("tÊÌ.ÂÛÕ.1, °C"	"PT040"	        43.7	48.7	54.1	45.9	48.5	53.5	56.3	60.1)
		("tÊÌ.ÂÛÕ.2, °C"	"PT041"	        47.8	56.9	59.6	54.1	55.9	62.3	65.7	70.2)
		("dPÑ.GÂ.ÊÌ, Ïà"	"PP081"	        2.844	3.150	2.892	3550	1.446	1.873	1.437	2.086)
		("GÂ.ÊÌ, ã/c"	"PQ020"	                406.3	606.0	668.9	853.0	582.3	696.6	632.2	758.1)
		("GÂ.ÊÌ.ÏÐ, ã/ñ"	"PQ020_pr"	135.6	99.9	82.8	80.7	48.1	51.7	43.6	52.6)
		("tÊÌ.ÎÁ.ÑÒ, °C"	"RT100"	        98.0	109.9	115.2	117.4	126.3	129.3	127.7	129.3)
		("KSAM, %"	"PA010"	                39.8	40.0	40.1	40.2	40.3	40.4	40.5	40.5)
		("KSAM_Ó, %"	"PA016"	                40.0	40.0	40.0	40.0	40.0	40.0	40.0	40.0)
		("tÂ.ÊÑ.ÂÛÕ, °C"	"PT010"	        161.6	274.5	338.4	395.8	400.0	400.0	400.0	400.0)
		("tÂ.ÂÎ.ÂÕ, °C"	"PT020"	                103.9	170.9	207.2	237.5	248.3	260.2	273.3	276.6)
		("dP2-ÊÄÒ1, êÏà"	"FP470"	        22.55	35.99	49.54	56.05	64.36	64.44	69.27	68.48)
		("dP2-ÊÂ2, êÏà"	"FP450"	                23.43	37.97	51.79	58.85	67.53	66.93	71.63	70.73)
		("dP2-ÊÃÒ3, êÏà"	"FP460"	        23.84	70.69	135.72	214.57	259.58	322.25	382.56	377.16)
		("tÂ.ÊÂ2, °C"	"PT050"	                37.8	38.8	39.9	40.6	41.6	42.3	43.6	48.1)
		("tÂ.ÊÄÒ1, °C"	"PT060"	                43.1	57.1	64.2	59.9	59.2	60.8	63.6	68.1)
		("tÂ.ÊÃÒ3, °C"	"PT070"	                39.2	49.8	56.6	57.4	63.0	66.1	69.5	71.7)
		("PÂ.ÊÂ2, êÏà"	"PP040"	                240.6	594.5	835.3	1095.4	1269.0	1421.0	1544.5	1537.7)
		("PÂ.ÊÄÒ1, êÏà"	"PP050"	                417.6	791.1	1038.5	1339.6	1517.1	1714.2	1849.5	1822.1)
		("PÂ.ÊÃÒ3, êÏà"	"PP060"	                240.6	625.7	918.0	1256.2	1474.9	1695.6	1879.0	1866.2)
		("PÂ.ÂÎ.ÂÕ, êÏà"	"PP070"	        212.8	545.1	765.6	1017.9	1185.6	1339.6	1458.2	1454.3)
		("GÂ.ÔÎÐÑ, ã/ñ"	"PQ010"	                56.7	100.7	132.7	163.3	162.5	202.5	217.3	212.4)
		("ÏÊÑ.1, êÏà"	"-"	                "-"	1.0	1.1	1.5	1.5	1.7	1.8	"-")
		("ÏÊÑ.2, êÏà"	"-"	                "-"	0.9	1.1	1.3	1.6	1.7	1.6	"-")
		("ÏÊÑ.3, êÏà"	"-"	                "-"	1.3	1.5	1.8	1.9	2.1	2.3	"-")
		("f, Ãö"	"-"	                "-"	"øóì"	"øóì"	"øóì"	"øóì"	"øóì"	"øóì"	"-")
		("EMNOx,15,dry, ìã/íì3 15 % Î2"	"-"	"-"	150	176	222	242	288	342	"-")
		("EMCO,15,dry, ìã/íì3 15 % Î2"	"-"	"-"	40.0	8	3	2	3	3	"-")
		("ôÎ2,dry, % îá."	"-"	        "-"	18.04	17.17	16.52	16.24	15.87	15.52	"-")
		("NeÊÌ, %"	"-"	                "-"	"-"	"-"	"-"	"-"	"-"	"-"	"-")))

;;;;;;;;;;;;;;;;;;;;;;;;;;;;;;;;;;;;;;;;;;;;;;;;;;;;;;;;;;;;;;;;;;;;;;;;;;;;;;;;

(defun make-var-by-str	(tbl)
  (mapcar (function (lambda (el / new-name name)
		      (setq name     (car el)
			    new-name  (GOOD-LAYER-NAME name))
		      (set (read new-name) (cddr el))
		      (list name (cadr el) new-name)))
	  tbl))

(make-var-by-str *tbl-b1*)

(GOOD-LAYER-NAME "tÊÌ.ÏÎÄØ.1, °C")

(setq x-p2  (GOOD-LAYER-NAME "p2,_êÏà"))
(setq y-p2 (mapcar (function GOOD-LAYER-NAME)'("nÊÌ, îá/ìèí" "PÂ.ÊÄÒ1, êÏà" "PÂ.ÊÂ2, êÏà" "PÂ.ÊÃÒ3, êÏà")))

'(("Äàòà" "-" "Äàòà")
  ("Âðåìÿ" "-" "Âðåìÿ")
  ("Ne, ÌÂò" "GQ010" "Ne__ÌÂò")
  ("nÊÂÄ, îá/ìèí" "EN2" "nÊÂÄ__îá-ìèí")
  ("nÊÍÄ, îá/ìèí" "EN1" "nÊÍÄ__îá-ìèí")
  ("t04, °C" "T04" "t04__°C")
  ("dt04max, °C" "dT04plus" "dt04max__°C")
  ("dt04min, °C" "dT04minus" "dt04min__°C")
  ("tÍÂ, °C" "T01" "tÍÂ__°C")
  ("p2, êÏà" "P02" "p2__êÏà")
  ("tÄÒ, °C" "FT020" "tÄÒ__°C")
  ("GÊÄÒ1, êã/÷" "G2" "GÊÄÒ1__êã-÷")
  ("pÄÒ1, êÏà" "FP240" "pÄÒ1__êÏà")
  ("KÄÒ, %" "FA020" "KÄÒ__%")
  ("ÊÄÒ.Ð, %" "FA026" "ÊÄÒ_Ð__%")
  ("tÃÒ, °C" "FT010" "tÃÒ__°C")
  ("GÊÃÒ3, êã/÷" "G1" "GÊÃÒ3__êã-÷")
  ("PÊÃÒ3, Ïà" "FP040" "PÊÃÒ3__Ïà")
  ("KÃÒ, %" "FA010" "KÃÒ__%")
  ("ÊÃÒ.Ð, %" "FA016" "ÊÃÒ_Ð__%")
  ("nÊÌ, îá/ìèí" "RN110" "nÊÌ__îá-ìèí")
  ("VÊÌ.Ã, ìì/ñ" "RB220" "VÊÌ_Ã__ìì-ñ")
  ("VÊÌ.Î, ìì/ñ" "RB230" "VÊÌ_Î__ìì-ñ")
  ("tÊÌ.ÏÎÄØ.1, °C" "RT210" "tÊÌ_ÏÎÄØ_1__°C")
  ("tÊÌ.ÏÎÄØ.2, °C" "RT220" "tÊÌ_ÏÎÄØ_2__°C")
  ("tÊÌ.ÂÕ.1, °C" "PT030" "tÊÌ_ÂÕ_1__°C")
  ("tÊÌ.ÂÕ.2, °C" "PT031" "tÊÌ_ÂÕ_2__°C")
  ("tÊÌ.ÂÛÕ.1, °C" "PT040" "tÊÌ_ÂÛÕ_1__°C")
  ("tÊÌ.ÂÛÕ.2, °C" "PT041" "tÊÌ_ÂÛÕ_2__°C")
  ("dPÑ.GÂ.ÊÌ, Ïà" "PP081" "dPÑ_GÂ_ÊÌ__Ïà")
  ("GÂ.ÊÌ, ã/c" "PQ020" "GÂ_ÊÌ__ã-c")
  ("GÂ.ÊÌ.ÏÐ, ã/ñ" "PQ020_pr" "GÂ_ÊÌ_ÏÐ__ã-ñ")
  ("tÊÌ.ÎÁ.ÑÒ, °C" "RT100" "tÊÌ_ÎÁ_ÑÒ__°C")
  ("KSAM, %" "PA010" "KSAM__%")
  ("KSAM_Ó, %" "PA016" "KSAM_Ó__%")
  ("tÂ.ÊÑ.ÂÛÕ, °C" "PT010" "tÂ_ÊÑ_ÂÛÕ__°C")
  ("tÂ.ÂÎ.ÂÕ, °C" "PT020" "tÂ_ÂÎ_ÂÕ__°C")
  ("dP2-ÊÄÒ1, êÏà" "FP470" "dP2-ÊÄÒ1__êÏà")
  ("dP2-ÊÂ2, êÏà" "FP450" "dP2-ÊÂ2__êÏà")
  ("dP2-ÊÃÒ3, êÏà" "FP460" "dP2-ÊÃÒ3__êÏà")
  ("tÂ.ÊÂ2, °C" "PT050" "tÂ_ÊÂ2__°C")
  ("tÂ.ÊÄÒ1, °C" "PT060" "tÂ_ÊÄÒ1__°C")
  ("tÂ.ÊÃÒ3, °C" "PT070" "tÂ_ÊÃÒ3__°C")
  ("PÂ.ÊÂ2, êÏà" "PP040" "PÂ_ÊÂ2__êÏà")
  ("PÂ.ÊÄÒ1, êÏà" "PP050" "PÂ_ÊÄÒ1__êÏà")
  ("PÂ.ÊÃÒ3, êÏà" "PP060" "PÂ_ÊÃÒ3__êÏà")
  ("PÂ.ÂÎ.ÂÕ, êÏà" "PP070" "PÂ_ÂÎ_ÂÕ__êÏà")
  ("GÂ.ÔÎÐÑ, ã/ñ" "PQ010" "GÂ_ÔÎÐÑ__ã-ñ")
  ("ÏÊÑ.1, êÏà" "-" "ÏÊÑ_1__êÏà")
  ("ÏÊÑ.2, êÏà" "-" "ÏÊÑ_2__êÏà")
  ("ÏÊÑ.3, êÏà" "-" "ÏÊÑ_3__êÏà")
  ("f, Ãö" "-" "f__Ãö")
  ("EMNOx,15,dry, ìã/íì3 15 % Î2" "-" "EMNOx_15_dry__ìã-íì3_15_%_Î2")
  ("EMCO,15,dry, ìã/íì3 15 % Î2" "-" "EMCO_15_dry__ìã-íì3_15_%_Î2")
  ("ôÎ2,dry, % îá." "-" "ôÎ2_dry__%_îá_")
  ("NeÊÌ, %" "-" "NeÊÌ__%"))

;;;;;;;;;;;;;;;;;;;;;;;;;;;;;;;;;;;;;;;;;;;;;;;;;;;;;;;;;;;;;;;;;;;;;;;;;;;;;;;;


;;;; Äàííûå äëÿ ïîñòðîåíèÿ ðàâèñèìîñòåé ýìèññèè
;;;; Ýìèññèè ïðè ðàáîòå ÃÒÄ íà ÄÒ
(setq dt-data '(("dt-t04__" 419.6 467.4 581.0 676.3 701.9 734.4 783.4)
                ("dt-Ne___" 0.000 0.980 4.020 7.990 10.98 13.97 16.82)
                ("dt-EMNOx" 300.0 281.0 287.0 342.0 395.0 520.0 658.0)
                ("dt-EMCO_" 143.0 63.00 9.000 3.000 4.000 5.000 7.000)))


(setq dt-t04-EMNOx (mapcar (function list) (cdr (assoc "dt-t04__" dt-data)) (cdr (assoc "dt-EMNOx" dt-data)))
      dt-t04-EMCO_ (mapcar (function list) (cdr (assoc "dt-t04__" dt-data)) (cdr (assoc "dt-EMCO_" dt-data))))

;;;; Ýìèññèè ïðè ðàáîòå ÃÒÄ íà ÃÒ

(setq dt-data '(("gt-t04__" 451.2 559.7 643.9 673.0 719.5 762.8)
                ("gt-Ne___" 1.000 4.000 8.020 11.00 13.99 16.52)
                ("gt-EMNOx" 150.0 176.0 222.0 242.0 288.0 342.0)
                ("gt-EMCO_" 40.00 8.000 3.000 2.000 3.000 3.000)))


(setq gt-t04-EMNOx (mapcar (function list) (cdr (assoc "gt-t04__" dt-data)) (cdr (assoc "gt-EMNOx" dt-data)))
      gt-t04-EMCO_ (mapcar (function list) (cdr (assoc "gt-t04__" dt-data)) (cdr (assoc "gt-EMCO_" dt-data))))

;;;;;;;;;;;;;;;;;;;;;;;;;;;;;;;;;;;;;;;;;;;;;;;;;;;;;;;;;;;;;;;;;;;;;;;;;;;;;;;;;;;;;;;;;;;;;;;;;;;;;;;;;;;;;;;;
;;;; Òåìïåðàòóðû ìåòàëëà ñòåíêè êîëëåêòîðîâ
;;;;;;;;;;;;;;;;;;;;;;;;;;;;;;;;;;;;;;;;;;;;;;;;;;;;;;;;;;;;;;;;;;;;;;;;;;;;;;;;;;;;;;;;;;;;;;;;;;;;;;;;;;;;;;;;

"Òàáëèöà Á.5 - Òåìïåðàòóðû ìåòàëëà ñòåíêè êîëëåêòîðîâ ïîäâîäà äèçåëüíîãî è ãàçîîáðàçíîãî òîïëèâà è êîëëåêòîðà ïîäâîäà âîçäóõà ÃÒÄ ÄÌ80Ë ¹1 ïðè ðàáîòå íà äèçåëüíîì òîïëèâå"
(setq dt-tmp-data
'(("Ne"		"ÌÂò"		0.000	1.000	3.980	8.010	11.00	14.02	16.79)
  ("nÊÍÄ"	"îá/ìèí"	4644.	5222.	6284.	7135.	6950.	6958.	7020.)
  ("nÊÂÄ"	"îá/ìèí"	7359.	7626.	8241.	8718.	8889.	9051.	9250.)
  ("t04"	"°C"		420.5	468.8	580.7	676.6	701.4	734.6	784.1)
  ("t02"	"°C"		270.6	300.4	365.2	425.0	443.1	457.6	483.28)
  ("Äàòà"	""		"11.08"	"04.08"	"04.08"	"04.08"	"04.08"	"11.08"	"11.08")
  ("Âðåìÿ"	""		"15:59"	"15:26"	"15:47"	"16:17"	"16:45"	"16:35"	"16:55")
  ("tÊÄÒ1.1"	"°C"		67.3	74.6	81.6	89.0	91.6	90.6	98.2)
  ("tÊÄÒ1.2"	"°C"		54.2	56.4	58.7	61.9	63.0	56.6	58.7)
  ("tÊÄÒ1.3"	"°C"		52.2	52.4	52.1	51.2	52.9	47.3	47.9)
;;;;("tÊÄÒ1.4"	"°C"		30.0	32.2	33.0	33.0	32.7	30.4	30.5)
;;;;("tÊÄÒ1.5"	"°C"		29.9	31.3	31.8	32.1	31.6	30.2	30.4)
  ("tÊÄÒ1.6"	"°C"		53.6	57.6	57.1	54.8	55.4	44.8	45.1)
  ("tÊÄÒ1.7"	"°C"		55.2	54.8	51.8	52.2	52.1	47.9	48.9)
  ("tÊÄÒ1.8"	"°C"		54.0	63.7	74.2	89.0	94.2	89.0	97.0)
								
  ("tÊÂ2.1"	"°C"		58.0	63.6	71.7	68.9	71.7	70.8	73.7)
  ("tÊÂ2.2"	"°C"		50.9	57.4	67.3	70.9	75.6	70.9	74.1)
  ("tÊÂ2.3"	"°C"		53.8	56.6	63.4	66.4	70.2	68.5	69.5)
;;;;("tÊÂ2.4"	"°C"		0.0	0.0	0.0	0.0	0.0	0.0	0.0)
;;;;("tÊÂ2.5"	"°C"		0.0	1300.0	0.0	1300.0	1300.0	0.0	0.0)
  ("tÊÂ2.6"	"°C"		50.6	67.1	73.0	69.3	76.0	78.9	82.2)
  ("tÊÂ2.7"	"°C"		51.5	58.5	62.7	69.7	73.0	72.2	76.3)
  ("tÊÂ2.8"	"°C"		54.0	55.0	55.2	54.4	54.2	53.9	54.9)
								
  ("tÊÃÒ3.1"	"°C"		60.9	68.0	80.4	81.7	89.9	87.0	92.4)
  ("tÊÃÒ3.2"	"°C"		55.7	59.5	66.9	64.9	67.4	65.4	67.5)
  ("tÊÃÒ3.3"	"°C"		52.4	57.7	66.6	68.6	73.1	70.7	72.9)
;;;;("tÊÃÒ3.4"	"°C"		33.4	33.6	32.5	32.2	31.2	31.6	31.3)
;;;;("tÊÃÒ3.5"	"°C"		71.0	39.6	49.9	45.6	49.7	118.1	125.7)
  ("tÊÃÒ3.6"	"°C"		58.8	71.0	83.0	83.9	86.6	85.6	90.3)
  ("tÊÃÒ3.7"	"°C"		60.1	68.9	68.6	80.7	85.0	90.9	97.7)
  ("tÊÃÒ3.8"	"°C"		53.8	59.6	66.3	70.9	71.8	78.7	80.7)))

(defun transpon (m) (apply 'mapcar (cons 'list m)))

(defun koll-rotare  (x)
  (if (>= x 5)
    (- x 9)
    (- x 1)))

(defun t-koll  (koll-str data)
  (transpon (mapcar (function (lambda (el)
                                (mapcar (function (lambda (el1) (list (koll-rotare el) el1)))
                                        (cddr (assoc (strcat koll-str "." (itoa el)) data)))))
                    '(1 2 3 6 7 8))))

(defun t-koll-sort  (koll-str data)
  (mapcar (function (lambda (el) (VL-SORT el (function (lambda (el1 el2) (< (car el1) (car el2)))))))
          (t-koll koll-str data)))

(defun t04-names  (data)
  (mapcar (function (lambda (el) (strcat "t04-" (rtos el)))) (cddr (assoc "t04" data))))

(defun make-t-koll  (koll-str data str-dt-gt)
  (mapcar (function
            (lambda (v-name data / v-str) (setq v-str (strcat str-dt-gt "-" koll-str "-" v-name)) (set (read v-str) data) v-str))
          (t04-names data)
          (t-koll-sort koll-str data)))

(mapcar (function (lambda (koll data str-dt-gt) (make-t-koll koll data str-dt-gt)))
        '("tÊÄÒ1" "tÊÂ2" "tÊÃÒ3")
        (list dt-tmp-data dt-tmp-data dt-tmp-data)
        '("dt" "dt" "dt"))

(setq dt-tÊÄÒ1 '("dt-tÊÄÒ1-t04-420.5"          "dt-tÊÄÒ1-t04-468.8"          "dt-tÊÄÒ1-t04-580.7"
                 "dt-tÊÄÒ1-t04-676.6"          "dt-tÊÄÒ1-t04-701.4"          "dt-tÊÄÒ1-t04-734.6"
                 "dt-tÊÄÒ1-t04-784.1")
      dt-tÊÂ2  '("dt-tÊÂ2-t04-420.5"         "dt-tÊÂ2-t04-468.8"         "dt-tÊÂ2-t04-580.7"
                 "dt-tÊÂ2-t04-676.6"         "dt-tÊÂ2-t04-701.4"         "dt-tÊÂ2-t04-734.6"
                 "dt-tÊÂ2-t04-784.1")
      dt-tÊÃÒ3 '("dt-tÊÃÒ3-t04-420.5"          "dt-tÊÃÒ3-t04-468.8"          "dt-tÊÃÒ3-t04-580.7"
                 "dt-tÊÃÒ3-t04-676.6"          "dt-tÊÃÒ3-t04-701.4"          "dt-tÊÃÒ3-t04-734.6"
                 "dt-tÊÃÒ3-t04-784.1"))


(mapcar (function (lambda (koll data str-dt-gt) (make-t-koll koll data str-dt-gt)))
        '("tÊÄÒ1" "tÊÂ2" "tÊÃÒ3")
        (list gt-tmp-data gt-tmp-data gt-tmp-data)
        '("gt" "gt" "gt"))

(setq gt-tÊÄÒ1 '("gt-tÊÄÒ1-t04-368.7"         "gt-tÊÄÒ1-t04-452.6"         "gt-tÊÄÒ1-t04-560.5"
                 "gt-tÊÄÒ1-t04-643.4"         "gt-tÊÄÒ1-t04-672.7"         "gt-tÊÄÒ1-t04-718.3"
                 "gt-tÊÄÒ1-t04-762.1"         ); "gt-tÊÄÒ1-t04-769"
      gt-tÊÂ2  '("gt-tÊÂ2-t04-368.7"         "gt-tÊÂ2-t04-452.6"         "gt-tÊÂ2-t04-560.5"
                 "gt-tÊÂ2-t04-643.4"         "gt-tÊÂ2-t04-672.7"         "gt-tÊÂ2-t04-718.3"
                 "gt-tÊÂ2-t04-762.1"         ); "gt-tÊÂ2-t04-769"
      gt-tÊÃÒ3 '("gt-tÊÃÒ3-t04-368.7"         "gt-tÊÃÒ3-t04-452.6"         "gt-tÊÃÒ3-t04-560.5"
                 "gt-tÊÃÒ3-t04-643.4"         "gt-tÊÃÒ3-t04-672.7"         "gt-tÊÃÒ3-t04-718.3"
                 "gt-tÊÃÒ3-t04-762.1"         )) ;"gt-tÊÃÒ3-t04-769"

"Òàáëèöà Á.8 – Òåìïåðàòóðû ìåòàëëà ñòåíêè êîëëåêòîðîâ ïîäâîäà äèçåëüíîãî è ãà-çîîáðàçíîãî òîïëèâà è êîëëåêòîðà ïîäâîäà âîçäóõà ÃÒÄ ÄÌ80Ë ¹1 ïðè ðàáîòå íà ãàçîîáðàçíîì òîïëèâå"
(setq gt-tmp-data
'(("Ne"		"ÌÂò"		0.00	1.01	4.00	7.98	10.98	14.00	16.53	16.51)
  ("nÊÍÄ"	"îá/ìèí"	2992	5200	6274	7018	6888	6906	6997	7017)
  ("nÊÂÄ"	"îá/ìèí"	6098	7575	8193	8644	8827	9045	9216	9250)
  ("t04"	"°C"		368.7	452.6	560.5	643.4	672.7	718.3	762.1	769)
  ("Äàòà"	""		"21.08"	"21.08"	"21.08"	"21.08"	"21.08"	"21.08"	"21.08"	"21.08")
  ("Âðåìÿ"	""		"11:09"	"11:28"	"11:47"	"11:58"	"12:18"	"12:33"	"12:53"	"16:19")
  ("tÊÄÒ1.1"	"°C"		42.8	65.7	81.4	92.5	107.3	112.4	124.4	128.9)
  ("tÊÄÒ1.2"	"°C"		37.1	56.6	72.8	78.2	87.2	88.6	96.0	101.3)
  ("tÊÄÒ1.3"	"°C"		34.4	50.6	64.5	65.4	68.8	70.3	75.2	79.4)
;;;;("tÊÄÒ1.4"	"°C"		29.2	29.4	29.9	29.6	29.8	33.0	25.2	49.0)
;;;;("tÊÄÒ1.5"	"°C"		29.1	29.3	29.6	29.5	29.9	31.2	26.9	31.6)
  ("tÊÄÒ1.6"	"°C"		42.7	64.3	84.3	80.3	81.3	91.1	95.1	97.4)
  ("tÊÄÒ1.7"	"°C"		51.6	75.1	92.0	101.1	115.0	122.4	130.2	130.1)
  ("tÊÄÒ1.8"	"°C"		27.2	32.8	37.1	36.5	37.4	37.0	36.9	32.5)
									
  ("tÊÂ2.1"	"°C"		36.9	54.0	58.4	64.9	65.1	66.9	70.6	75.5)
  ("tÊÂ2.2"	"°C"		22.3	29.3	33.9	34.1	35.1	35.1	35.1	31.0)
  ("tÊÂ2.3"	"°C"		36.8	50.4	59.2	63.4	64.5	64.4	66.5	69.7)
;;;;("tÊÂ2.4"	"°C"		0.0	0.0	0.0	0.0	0.0	0.0	0.0	0.0)
;;;;("tÊÂ2.5"	"°C"		3.4	0.0	0.0	0.0	3.9	21.0	52.0	39.6)
  ("tÊÂ2.6"	"°C"		34.2	52.0	63.4	62.7	68.3	76.2	80.9	80.5)
  ("tÊÂ2.7"	"°C"		36.6	49.0	55.8	59.0	61.5	67.4	71.2	73.7)
  ("tÊÂ2.8"	"°C"		44.3	62.3	82.9	93.2	111.9	120.3	134.7	139.2)
									
  ("tÊÃÒ3.1"	"°C"		27.9	36.4	38.2	40.7	41.4	41.4	42.1	39.2)
  ("tÊÃÒ3.2"	"°C"		40.1	54.5	60.6	63.1	62.0	62.6	65.6	69.4)
  ("tÊÃÒ3.3"	"°C"		25.1	32.0	36.5	37.1	37.2	37.8	37.7	32.5)
;;;;("tÊÃÒ3.4"	"°C"		32.7	32.5	31.9	31.7	31.3	216.1	0.0	203.2)
;;;;("tÊÃÒ3.5"	"°C"		33.2	33.4	33.6	33.7	33.5	39.3	26.2	40.7)
  ("tÊÃÒ3.6"	"°C"		31.3	39.9	44.4	42.5	45.4	45.8	46.5	43.2)
  ("tÊÃÒ3.7"	"°C"		28.7	35.1	37.1	36.0	37.3	39.4	39.9	35.9)
  ("tÊÃÒ3.8"	"°C"		37.3	50.3	63.8	63.5	64.1	67.0	71.5	70.3)))
