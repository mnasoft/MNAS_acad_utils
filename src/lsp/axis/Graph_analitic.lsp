(setq analitic:*setup*
       '(("t-min" . 10.0)
         ("t-max" . 20.0)
         ("n" . 50)
         ("fl" . 0)
         ("x(t)" . "x_p")
         ("y(t)" . "y_p")
         ("defun" . "(progn (defun x_p(p)p) (defun y_p(p)p) )")))


(defun analitic:setup  ()
  (set_tile "analitic:t-min-eb" (rtos t-min))
  (set_tile "analitic:n-eb" (rtos n))
  (set_tile "analitic:t-max-eb" (rtos t-max))
  (set_tile "analitic:function-eb" def)
  (set_tile "analitic:x-function-eb" x-t)
  (set_tile "analitic:y-function-eb" y-t)
  (cond ((= fl 0) (set_tile "analitic:proportional-rb" "1"))
        ((= fl 1) (set_tile "analitic:logarithmic-rb" "1"))))

(defun analitic:evaluate-btn () (eval (read def)))

(defun analitic:reculc-btn  (/ i nn xf yf) ;;;; (FL L_PTS L_TXT N T-MAX T-MIN TT X-T Y-T )
  (setq xf    (eval (read x-t))
        yf    (eval (read y-t))
        l_pts nil)
  (if (null xf)
    (exit))
  (if (null yf)
    (exit))
  (setq i 0)
  (if (<= n 0)
    (setq nn 1)
    (setq nn n))
  (while (<= i n)
    (if (= fl 0)
      (setq tt (+ t-min (/ (* i (- t-max t-min)) nn)))
      (setq tt (* t-min (exp (/ (* (log (/ t-max t-min)) i) nn)))))
    (setq l_pts (cons (list tt (xf tt) (yf tt)) l_pts))
    (setq i (1+ i)))
  (setq l_pts (reverse l_pts))
  (setq l_txt (mapcar (function (lambda (el) (strcat (rtos (car el)) " " (rtos (cadr el)) " " (rtos (caddr el)))))
                      l_pts))
  (start_list "analitic:points-lb")
  (mapcar 'add_list l_txt)
  (end_list))

(defun analitic:t-min-eb () (setq t-min (atof (get_tile "analitic:t-min-eb"))))

(defun analitic:n-eb () (setq n (atoi (get_tile "analitic:n-eb"))))

(defun analitic:t-max-eb () (setq t-max (atof (get_tile "analitic:t-max-eb"))))

(defun analitic:function-eb () (setq def (get_tile "analitic:function-eb")))

(defun analitic:proportional-rb () (setq fl 0))

(defun analitic:logarithmic-rb () (setq fl 1))

(defun analitic:ac-tile  ()
  (action_tile "analitic:evaluate-btn" "(analitic:evaluate-btn)")
  (action_tile "analitic:t-min-eb" "(analitic:t-min-eb)")
  (action_tile "analitic:n-eb" "(analitic:n-eb)")
  (action_tile "analitic:t-max-eb" "(analitic:t-max-eb)")
  (action_tile "analitic:function-eb" "(analitic:function-eb)")
  (action_tile "analitic:reculc-btn" "(analitic:reculc-btn)")
  (action_tile "analitic:proportional-rb" "(analitic:proportional-rb)")
  (action_tile "analitic:logarithmic-rb" "(analitic:logarithmic-rb)"))

;;; an:analitic	- Функция выводит на экран диалог в котором можно задать в
;;;		  параметрическом виде функцию 2-х координат.
;;;		  Возвращает список координат.
;;; (analitic:main)
(defun analitic:main (/ l1 t-min t-max n x-t y-t def fl l_pts act do_dialog dcl_id ret)
  (setq l1 analitic:*setup*)
  (if l1
    (setq t-min (cdr (assoc "t-min" l1))
          t-max (cdr (assoc "t-max" l1))
          fl    (cdr (assoc "fl" l1))
          n     (cdr (assoc "n" l1))
          x-t   (cdr (assoc "x(t)" l1))
          y-t   (cdr (assoc "y(t)" l1))
          def   (cdr (assoc "defun" l1))))
  (setq dcl_id (load_dialog (findfile (utils:path-src-lsp "axis/axis_graph_1.dcl"))))
  (if (< dcl_id 0)
    (exit))
  (setq do_dialog t)
  (while do_dialog
    (if (not (new_dialog "analitic" dcl_id))
      (exit))
    (analitic:setup)
    (analitic:ac-tile)
    (setq act (start_dialog))
    (cond ((= act 0) (setq do_dialog nil) (setq ret (list nil l1)))
          ((= act 1)
           (setq do_dialog nil)
           (analitic:reculc-btn)
           (setq ret (mapcar (function (lambda (el) (list (cadr el) (caddr el)))) l_pts))
           (setq l1 (dsubst l1
                            (list (cons "t-min" t-min)
                                  (cons "t-max" t-max)
                                  (cons "n" n)
                                  (cons "fl" fl)
                                  (cons "x(t)" x-t)
                                  (cons "y-t" y-t)
                                  (cons "defun" def)))
                 analitic:*setup* l1))))
  (unload_dialog dcl_id)
  ret)
