(setq axis-podp:*shcala_setup*
       '(("zas_right" "1")
         ("zas_right_len" "2")
         ("zas_left" "1")
         ("zas_left_len" "2")
         ("zas_x_min" "0")
         ("zas_x_max" "100")
         ("zas_n_div" "10")
         ("zas_lst" "0" ("0" "10" "20" "30" "40" "50" "60" "70" "80" "90" "100"))
         ("text_dist_from_ax" "-4.0")
         ("text_hight" "3.5")
         ("text_angle" "0")
         ("text_x_min" "0")
         ("text_x_max" "100")
         ("text_n_div" "10")
         ("text_lst" "0" ("0" "10" "20" "30" "40" "50" "60" "70" "80" "90" "100"))
         ("podp_text_start" "0")
         ("podp_text_middle" "1")
         ("podp_text_end" "0")
         ("podp_text_dist_from_ax" "15")
         ("podp_text_hight" "5")
         ("podp_text_angle" "0")
         ("zas_draw" "1")
         ("text_draw" "1")
         ("podp_text_draw" "1")))

(setq axis-podp:*sc-x-ename* nil)

(setq axis-podp:*sc-y-ename* nil)

(defun axis-podp:btn-select-x-axis  ()
  (princ "\naxis-podp:btn_select_x_axis")
  (setq axis-podp:*sc-x-ename*
         (axis:sel "\nВыберите шкалу x:")
        sc_x (axis:get axis-podp:*sc-x-ename*)))

(defun axis-podp:btn-select-y-axis  ()
  (princ "\nbtn_select_y_axis")
  (setq axis-podp:*sc-y-ename*
         (axis:sel "\nВыберите шкалу y:")
        sc_y (axis:get axis-podp:*sc-y-ename*)))

(defun axis-podp:btn-delete () (command-s "erase" ss_zas ss_text ss_podp_text ""))

(defun axis-podp:draw-zas  (ss_zas   sc_x     sc_y     ll_ax_shcala      /        n_div    pt       pt_0     pt_1
                            scx_end  scx_st   scy_end  scy_st   x_max    x_min    en       el       lst      lst-i
                            lst-len  lst-rez)
  (setq x_min (atof (cadr (assoc "zas_x_min" ll_ax_shcala)))
        x_max (atof (cadr (assoc "zas_x_max" ll_ax_shcala)))
        n_div (atoi (cadr (assoc "zas_n_div" ll_ax_shcala))))
  (setq scx_st  (cdr (assoc 10 sc_x))
        scx_end (cdr (assoc 11 sc_x))
        scy_st  (cdr (assoc 10 sc_y))
        scy_end (cdr (assoc 11 sc_y)))
  (progn (setq lst     (sub_div x_min x_max n_div 0)
               lst-len (length lst)
               lst-i   -1)
         (while (< (setq lst-i (1+ lst-i)) lst-len)
           (setq el      (nth lst-i lst)
                 lst-rez (cons (progn (setq pt   (sc:val_pt el sc_x)
                                            pt_0 (polar pt (angle scy_st scy_end) (atof (cadr (assoc "zas_right_len" ll_ax_shcala))))
                                            pt_1 (polar pt (angle scy_end scy_st) (atof (cadr (assoc "zas_left_len" ll_ax_shcala)))))
                                      (if (and (= "1" (cadr (assoc "zas_right" ll_ax_shcala)))
                                               (= "1" (cadr (assoc "zas_draw" ll_ax_shcala))))
                                        (progn (dr:line pt pt_0 1) (setq ss_zas (ssadd (entlast) ss_zas))))
                                      (if (and (= "1" (cadr (assoc "zas_left" ll_ax_shcala)))
                                               (= "1" (cadr (assoc "zas_draw" ll_ax_shcala))))
                                        (progn (dr:line pt pt_1 2) (setq ss_zas (ssadd (entlast) ss_zas)))))
                               lst-rez)))
         (setq lst-rez (reverse lst-rez))))


(defun axis-podp:draw-text  (ss_text sc_x sc_y ll_ax_shcala / n_div pt pt_0 scx_end scx_st scy_end scy_st x_max x_min)
  (setq x_min (atof (cadr (assoc "text_x_min" ll_ax_shcala)))
        x_max (atof (cadr (assoc "text_x_max" ll_ax_shcala)))
        n_div (atoi (cadr (assoc "text_n_div" ll_ax_shcala))))
  (setq scx_st  (cdr (assoc 10 sc_x))
        scx_end (cdr (assoc 11 sc_x))
        scy_st  (cdr (assoc 10 sc_y))
        scy_end (cdr (assoc 11 sc_y)))
  (mapcar (function (lambda (el / PT PT_0)
                      (setq pt   (sc:val_pt el sc_x)
                            pt_0 (polar pt (angle scy_st scy_end) (atof (cadr (assoc "text_dist_from_ax" ll_ax_shcala)))))
                      (if (= "1" (cadr (assoc "text_draw" ll_ax_shcala)))
                        (progn (dr:text (rtos el)
                                        pt_0
                                        (atof (cadr (assoc "text_hight" ll_ax_shcala)))
                                        (angtof (cadr (assoc "text_angle" ll_ax_shcala)))
                                        -1 0)
                               (dr:ch_prop (list (cons 72 1) (cons 73 2) (cons 11 pt_0)))
                               (setq ss_text (ssadd (entlast) ss_text))))))
          (sub_div x_min x_max n_div 0)))


(defun axis-podp:draw-podp-text  (ss_podp_text sc_x sc_y ll_ax_shcala / pt pt_0 scx_end scx_st scy_end scy_st)
  (setq scx_st  (cdr (assoc 10 sc_x))
        scx_end (cdr (assoc 11 sc_x))
        scy_st  (cdr (assoc 10 sc_y))
        scy_end (cdr (assoc 11 sc_y)))
  (cond ((= (cadr (assoc "podp_text_start" ll_ax_shcala)) "1") (setq pt scx_st))
        ((= (cadr (assoc "podp_text_middle" ll_ax_shcala)) "1")
         (setq pt (vect_sc/ (vect_+ scx_st scx_end) 2.0)))
        ((= (cadr (assoc "podp_text_end" ll_ax_shcala)) "1") (setq pt scx_end)))
  (setq pt_0 (polar pt (angle scy_st scy_end) (atof (cadr (assoc "podp_text_dist_from_ax" ll_ax_shcala)))))
  (if (= "1" (cadr (assoc "podp_text_draw" ll_ax_shcala)))
    (progn (dr:text (cdr (assoc 1 sc_x))
                    pt_0
                    (atof (cadr (assoc "podp_text_hight" ll_ax_shcala)))
                    (angtof (cadr (assoc "podp_text_angle" ll_ax_shcala)))
                    -1 0)
           (dr:ch_prop (list (cons 72 1) (cons 73 2) (cons 11 pt_0)))
           (setq ss_podp_text (ssadd (entlast) ss_podp_text))))
  (mapcar (function (lambda (el / pt pt_0)
                      (setq pt   (sc:val_pt el sc_x)
                            pt_0 (polar pt (angle scy_st scy_end) (atof (cadr (assoc "text_dist_from_ax" ll_ax_shcala)))))))
          (sub_div x_min x_max n_div 0)))

(defun axis-podp:btn-draw  (sc_x sc_y ll_ax_shcala)
  (princ "\nbtn_darw")
  (if (and sc_x sc_y)
    (progn (axis-podp:draw-zas ss_zas sc_x sc_y ll_ax_shcala)
           (axis-podp:draw-text ss_text sc_x sc_y ll_ax_shcala)
           (axis-podp:draw-podp-text ss_podp_text sc_x sc_y ll_ax_shcala))
    ))

;; axis-podp:ac-zas-draw-hide-show()	- Замораживает или размораживает некоторые tile.
(defun axis-podp:ac-zas-draw-hide-show  (/ tmp ll-zas_draw)
  (setq tmp         (cadr (assoc "zas_draw" ll_ax_shcala))
        ll-zas_draw (list "zas_right" "zas_right_len" "zas_left" "zas_left_len" "zas_x_min" "zas_x_max" "zas_n_div"
                          "zas_lst"))
  (cond ((= tmp "0") (mapcar (function (lambda (el) (mode_tile el 1))) ll-zas_draw))
        ((= tmp "1") (mapcar (function (lambda (el) (mode_tile el 0))) ll-zas_draw))))

;; axis-podp:ac-text-draw-hide-show()	- Замораживает или размораживает некоторые tile.
(defun axis-podp:ac-text-draw-hide-show  (/ tmp ll-text_draw)
  (setq tmp          (cadr (assoc "text_draw" ll_ax_shcala))
        ll-text_draw (list "text_dist_from_ax" "text_hight" "text_angle" "text_x_min" "text_x_max" "text_n_div"
                           "text_lst"))
  (cond ((= tmp "0") (mapcar (function (lambda (el) (mode_tile el 1))) ll-text_draw))
        ((= tmp "1") (mapcar (function (lambda (el) (mode_tile el 0))) ll-text_draw))))


;;	axis-podp:ac-text-draw-hide-show()	- Замораживает или размораживает некоторые tile.
(defun axis-podp:ac-text-draw-hide-show  (/ tmp ll-podp_text_draw)
  (setq tmp               (cadr (assoc "podp_text_draw" ll_ax_shcala))
        ll-podp_text_draw (list "podp_text_start"          "podp_text_middle"         "podp_text_end"
                                "podp_text_dist_from_ax"   "podp_text_hight"          "podp_text_angle"))
  (cond ((= tmp "0") (mapcar (function (lambda (el) (mode_tile el 1))) ll-podp_text_draw))
        ((= tmp "1") (mapcar (function (lambda (el) (mode_tile el 0))) ll-podp_text_draw))))

(defun axis-podp:setup  ()
  (mapcar (function (lambda (el)
                      (cond ((= 2 (length el)) (set_tile (car el) (cadr el)))
                            ((= 3 (length el))
                             (start_list (car el))
                             (mapcar (function add_list) (caddr el))
                             (end_list)
                             (set_tile (car el) (cadr el))))))
          ll_ax_shcala)
  (axis-podp:ac-zas-draw-hide-show)
  (axis-podp:ac-text-draw-hide-show)
  (axis-podp:ac-text-draw-hide-show))


(defun axis-podp:ac-tile  ()
  (mapcar (function (lambda (el) (action_tile (car el) "(axis-podp:all-ac)"))) ll_ax_shcala)
  (action_tile "btn_select_x_axis" "(done_dialog 2)")
  (action_tile "btn_select_y_axis" "(done_dialog 3)")
  (action_tile "btn_draw" "(done_dialog 4)")
  (action_tile "btn_delete" "(done_dialog 5)"))

(defun axis-podp:validate  (/ ll_val TMP)
  (setq tmp (atof (cadr (assoc "zas_right_len" ll_ax_shcala))))
  (if (<= tmp 0.0)
    (setq ll_val (cons (list "zas_right_len" "1.0") ll_val))
    (setq ll_val (cons (list "zas_right_len" (rtos tmp)) ll_val)))
  (setq tmp (atof (cadr (assoc "zas_left_len" ll_ax_shcala))))
  (if (<= tmp 0.0)
    (setq ll_val (cons (list "zas_left_len" "1.0") ll_val))
    (setq ll_val (cons (list "zas_left_len" (rtos tmp)) ll_val)))
  (setq ll_val (cons (list "zas_x_min" (rtos (atof (cadr (assoc "zas_x_min" ll_ax_shcala))))) ll_val)
        ll_val (cons (list "zas_x_max" (rtos (atof (cadr (assoc "zas_x_max" ll_ax_shcala))))) ll_val))
  (setq tmp (atoi (cadr (assoc "zas_n_div" ll_ax_shcala))))
  (if (<= tmp 0)
    (setq ll_val (cons (list "zas_n_div" "1") ll_val))
    (setq ll_val (cons (list "zas_n_div" (itoa tmp)) ll_val)))
  (setq ll_val (cons (list "text_dist_from_ax" (rtos (atof (cadr (assoc "text_dist_from_ax" ll_ax_shcala)))))
                     ll_val))
  (setq tmp (atof (cadr (assoc "text_hight" ll_ax_shcala))))
  (if (<= tmp 0.0)
    (setq ll_val (cons (list "text_hight" "3.5") ll_val))
    (setq ll_val (cons (list "text_hight" (rtos tmp)) ll_val)))
  (setq ll_val (cons (list "text_angle" (angtos (angtof (cadr (assoc "text_angle" ll_ax_shcala))))) ll_val)
        ll_val (cons (list "text_x_min" (rtos (atof (cadr (assoc "text_x_min" ll_ax_shcala))))) ll_val)
        ll_val (cons (list "text_x_max" (rtos (atof (cadr (assoc "text_x_max" ll_ax_shcala))))) ll_val))
  (setq tmp (atoi (cadr (assoc "text_n_div" ll_ax_shcala))))
  (if (<= tmp 0)
    (setq ll_val (cons (list "text_n_div" "1") ll_val))
    (setq ll_val (cons (list "text_n_div" (itoa tmp)) ll_val)))
  (setq ll_val
         (cons (list "podp_text_dist_from_ax" (rtos (atof (cadr (assoc "podp_text_dist_from_ax" ll_ax_shcala)))))
               ll_val))
  (setq tmp (atof (cadr (assoc "podp_text_hight" ll_ax_shcala))))
  (if (<= tmp 0.0)
    (setq ll_val (cons (list "podp_text_hight" "5.0") ll_val))
    (setq ll_val (cons (list "podp_text_hight" (rtos tmp)) ll_val)))
  (setq ll_val (cons (list "podp_text_angle" (angtos (angtof (cadr (assoc "podp_text_angle" ll_ax_shcala)))))
                     ll_val))
  (setq ll_ax_shcala (dsubst ll_ax_shcala ll_val))
  (setq tmp    (assoc "zas_lst" ll_ax_shcala)
        ll_val (cons (list (car tmp)
                           (cadr tmp)
                           (mapcar 'rtos
                                   (sub_div (atof (cadr (assoc "zas_x_min" ll_ax_shcala)))
                                            (atof (cadr (assoc "zas_x_max" ll_ax_shcala)))
                                            (atoi (cadr (assoc "zas_n_div" ll_ax_shcala)))
                                            0)))
                     ll_val)
        tmp    (assoc "text_lst" ll_ax_shcala)
        ll_val (cons (list (car tmp)
                           (cadr tmp)
                           (mapcar 'rtos
                                   (sub_div (atof (cadr (assoc "text_x_min" ll_ax_shcala)))
                                            (atof (cadr (assoc "text_x_max" ll_ax_shcala)))
                                            (atoi (cadr (assoc "text_n_div" ll_ax_shcala)))
                                            0)))
                     ll_val))
  (setq ll_ax_shcala (dsubst ll_ax_shcala ll_val)))

(defun axis-podp:all-ac  ()
  (setq ll_ax_shcala
         (mapcar (function (lambda (el)
                             (cond ((= 2 (length el)) (list (car el) (get_tile (car el))))
                                   ((= 3 (length el)) (list (car el) (get_tile (car el)) (caddr el))))))
                 ll_ax_shcala))
  (axis-podp:validate)
  (axis-podp:setup))

;;;;;;("ax_shcala" "Производит подпись шкалы." "Шкалы")
(defun c:ax_shcala  (/                  ;
                     dcl_id             ;
                     ll_ax_shcala       ;
                     exit_dialog        ;
                     sc_x               ;
                     sc_y               ;
                     ss_zas             ;
                     ss_text            ;
                     ss_podp_text       ;
)                                       ;
  (setq ss_zas (ssadd)
        ss_text (ssadd)
        ss_podp_text
         (ssadd))
  (if axis-podp:*sc-x-ename*
    (setq sc_x (axis:get axis-podp:*sc-x-ename*)))
  (if axis-podp:*sc-y-ename*
    (setq sc_y (axis:get axis-podp:*sc-y-ename*)))
  (setq ll_ax_shcala axis-podp:*shcala_setup*)
  (setq dcl_id (load_dialog (findfile (utils:path-src-lsp "axis/axis_podp.dcl"))))
  (if (< dcl_id 0)
    (exit))
  (while (null exit_dialog)
    (if (not (new_dialog "axis_podp" dcl_id))
      (exit))
    (axis-podp:setup)
    (axis-podp:ac-tile)
    (setq ac (start_dialog))
    (cond ((= ac 0) (setq exit_dialog t) (axis-podp:btn-delete))
          ((= ac 1) (setq axis-podp:*shcala_setup* ll_ax_shcala) (setq exit_dialog t))
          ((= ac 2) (axis-podp:btn-select-x-axis))
          ((= ac 3) (axis-podp:btn-select-y-axis))
          ((= ac 4) (axis-podp:btn-draw SC_X SC_Y ll_ax_shcala))
          ((= ac 5) (axis-podp:btn-delete)))))
