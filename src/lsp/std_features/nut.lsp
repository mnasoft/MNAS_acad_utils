(defun c:nut (/ s h m p)
  (setq s (getdist "Введите размер под ключ:"))
  (setq h (getdist "Введите высоту гайки:"))
  (setq m (getdist "Введите диаметр резьбы:"))
  (setq p (getdist "Шаг резьбы:"))
  (setq p0 (getpoint "Укажите расположение гайки:"))
  (command-s "_POLYGON" 6 "_non" p0 "_c" "_non" (polar p0 0 (/ s 2)))
  (command-s "_circle" "_non" p0 (- (*  m 0.5) (* 0.7 p) ))
  (command-s "_circle" "_non" p0  (*  m 0.5) )
  (setq dl (+ 3.0 (* s 0.57735)))
  (command-s "_line" "_non" (polar p0 pi dl ) "_non" (polar p0 0.0 dl) "")
  (command-s "_line" "_non" (polar p0 (* pi -0.5) dl ) "_non" (polar p0 (* pi 0.5) dl) "")
) 
;|«Visual LISP© Format Options»
(105 2 15 2 nil "end of" 90 9 0 0 0 T T nil T)
;*** НЕ добавляйте текст под комментариями! ***|;
