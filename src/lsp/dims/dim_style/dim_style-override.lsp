(defun dim-restore () (command-s "-dimstyle" "_Restore" (getvar "dimstyle")))

(defun toh-0 () (dim-restore) (command-s "DIMTOH" 0) (command-s "_dim1" "_update" ss ""))

(defun toh-1 () (dim-restore) (command-s "DIMTOH" 1) (command-s "_dim1" "_update" ss ""))
;;;Расположение размерного текста горизонтально.
(defun c:dim-toh  (/ do func_list i n ss x)
  (setq ss (ssget))
  (setq func_list '((1 . toh-0) (2 . toh-1)))
  (setq do t
        i  1
        n  2)
  (while do
    (initget "Next Exit")
    (setq x (getkword "Next Exit <Next>:"))
    (if (null x)
      (setq x "Next"))
    (cond ((= x "Next")
           (apply (cdr (assoc i func_list)) nil)
           (command-s "_redraw")
           (setq i (1+ i))
           (if (> i n)
             (setq i 1)))
          ((= x "Exit") (dim-restore) (setq do nil)))))


(defun c:dim-rad-hor  ()
  (dim-restore)
  (command-s "DIMTMOVE" 1)
  (command-s "DIMTOH" 1)
  (command-s "DIMTOFL" 0)
  (command-s "DIMCEN" 0.0)
  (command-s "_dimradius"))

(defun c:dim-rad-rad  ()
  (dim-restore)
  (command-s "DIMTMOVE" 1)
  (command-s "DIMTOH" 0)
  (command-s "DIMTOFL" 0)
  (command-s "DIMCEN" 0.0)
  (command-s "_dimradius"))

;;;Подавление|восстановление стрелок и линий выносок.
(defun c:DIM-SD_SE  (/ x do ss)
  (setq ss (ssget))
  (setq func_list '((1 . SD1-0_SE1-0_SD2-0_SE2-0)
                    (2 . SD1-1_SE1-1_SD2-0_SE2-0)
                    (3 . SD1-0_SE1-0_SD2-1_SE2-1)
                    (4 . SD1-0_SE1-1_SD2-1_SE2-0)
                    (5 . SD1-1_SE0-1_SD2-0_SE2-1)))
  (setq do t
        i  1
        n  5)
  (while do
    (initget "Next Exit")
    (setq x (getkword "Next Exit <Next>:"))
    (if (null x)
      (setq x "Next"))
    (cond ((= x "Next")
           (apply (cdr (assoc i func_list)) nil)
           (command-s "_redraw")
           (setq i (1+ i))
           (if (> i n)
             (setq i 1)))
          ((= x "Exit") (dim-restore) (setq do nil)))))

(defun SD1-0_SE1-0_SD2-0_SE2-0  ()
  (dim-restore)
  (command-s "DIMSD1" 0)
  (command-s "DIMSE1" 0)
  (command-s "DIMSD2" 0)
  (command-s "DIMSE2" 0)
  (command-s "_dim1" "_update" ss ""))

(defun SD1-1_SE1-1_SD2-0_SE2-0  ()
  (dim-restore)
  (command-s "DIMSD1" 1)
  (command-s "DIMSE1" 1)
  (command-s "DIMSD2" 0)
  (command-s "DIMSE2" 0)
  (command-s "_dim1" "_update" ss ""))

(defun SD1-0_SE1-0_SD2-1_SE2-1  ()
  (dim-restore)
  (command-s "DIMSD1" 0)
  (command-s "DIMSE1" 0)
  (command-s "DIMSD2" 1)
  (command-s "DIMSE2" 1)
  (command-s "_dim1" "_update" ss ""))

(defun SD1-0_SE1-1_SD2-1_SE2-0  ()
  (dim-restore)
  (command-s "DIMSD1" 0)
  (command-s "DIMSE1" 1)
  (command-s "DIMSD2" 1)
  (command-s "DIMSE2" 0)
  (command-s "_dim1" "_update" ss ""))

(defun SD1-1_SE0-1_SD2-0_SE2-1  ()
  (dim-restore)
  (command-s "DIMSD1" 1)
  (command-s "DIMSE1" 0)
  (command-s "DIMSD2" 0)
  (command-s "DIMSE2" 1)
  (command-s "_dim1" "_update" ss ""))
