(defun ac_b_1_1	 ()
  (setq ar_ang_s (angtof "10"))
  (setq ar_ang_e (angtof "60"))
  (setq ar_size (atof "5"))
  (set_tile "e_1_1" (angtos ar_ang_s))
  (set_tile "e_1_2" (angtos ar_ang_e))
  (set_tile "e_1_3" (rtos ar_size)))

(defun ac_e_1_1 () (setq ar_ang_s (angtof (get_tile "e_1_1"))) (set_tile "e_1_1" (angtos ar_ang_s)))

(defun ac_e_1_2 () (setq ar_ang_e (angtof (get_tile "e_1_2"))) (set_tile "e_1_2" (angtos ar_ang_e)))

(defun ac_e_1_3 () (setq ar_size (atof (get_tile "e_1_3"))) (set_tile "e_1_3" (angtos ar_size)))

(defun dia_arrow  (param / arrow_dcl_id act)
  (setq	ar_ang_s (nth 0 param)
	ar_ang_e (nth 1 param)
	ar_size	 (nth 2 param))
  (setq arrow_dcl_id (load_dialog (findfile (utils:path-src-lsp "DIMS/welding/welding.dcl"))))
  (if (< arrow_dcl_id 0)
    (exit))
  (if (not (new_dialog "arrow_setup" arrow_dcl_id))
    (exit))
  (set_tile "e_1_1" (angtos ar_ang_s))
  (set_tile "e_1_2" (angtos ar_ang_e))
  (set_tile "e_1_3" (rtos ar_size))
  (action_tile "b_1_1" "(ac_b_1_1)")
  (action_tile "e_1_1" "(ac_e_1_1)")
  (action_tile "e_1_2" "(ac_e_1_2)")
  (action_tile "e_1_3" "(ac_e_1_3)")
  (setq act (start_dialog))
  (cond	((= act 0) (setq param param))
	((= act 1) (setq param (list ar_ang_s ar_ang_e ar_size))))
  (unload_dialog arrow_dcl_id)
  param)
