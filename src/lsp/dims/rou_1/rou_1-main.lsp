;;;;;;("rou" "Простановка обозначения шероховатости." "Размеры")
(defun c:rou  (/                        ;
               dcl_id                   ; id діалогу
               do_dialog                ; Прапорець виконання діалогу
               p1                       ; Перша точка
               p2                       ; Друга точка
               fl                       ;
               fl_nm                    ;
               old_err                  ; Обробник помилок
               kw
               str_kw
               osm
               reg_root                ; Шлях до налаштувань в реєстрі
               rou_registry)
  (err-init '("cmdecho" "osmode"))
  (set-sys-var-lst '(("cmdecho" 0)))
  (setq reg_root
        (strcat "HKEY_CURRENT_USER\\Software\\MNASoft\\Dims\\Rou"
                "\\"
                utils-locale))
  (setq rou_registry
      (list
       (list 'rou_1:dia_sher_pos '(-1 -1))
       (list 'setup_lst
             (list (list "rb_1_Ra" "1")
                   (list "rb_1_Rz" "0")
                   (list "pl_1_RaRz" "1"
                         (list "1" "2" "3" "4"))
                   (list "tgl_1_max_val" "1")
                   (list "eb_1_max_val" "10")
                   (list "pl_1_max_val"
                         "3"
                         (list
                          "80"
                          "40"
                          "20"
                          "10"
                          "5"
                          "2,5"
                          "1,25"
                          "0,63"
                          "0,32"
                          "0,16"
                          "0,08"))
                   (list "tgl_1_min_val" "0")         
                   (list "eb_1_min_val" "5")          
                   (list "pl_1_min_val"
                         "4"
                         (list "80"
                               "40"
                               "20"
                               "10"
                               "5"
                               "2,5"
                               "1,25"
                               "0,63"
                               "0,32"
                               "0,16"
                               "0,08")) 
                   (list "tgl_1_spos_pol" "0")
                   (list "eb_1_spos_pol" "")  
                   (list "pl_1_spos_pol"
                         "0"
                         (list
                          (utils-locale-string '(("ru" "Шабрить")      ("uk" "Шабрувати")      ("en" "Scrape")) "Scrape")
                          (utils-locale-string '(("ru" "Развертывать") ("uk" "Розвертати")     ("en" "Ream"))   "Ream")
                          (utils-locale-string '(("ru" "Протягивать")  ("uk" "Протягувати")    ("en" "Broach")) "Broach")
                          (utils-locale-string '(("ru" "Шлифовать")    ("uk" "Шліфувати")      ("en" "Grind"))  "Grind")
                          (utils-locale-string '(("ru" "Притереть")    ("uk" "Притирати")      ("en" "Lap"))    "Lap")
                          (utils-locale-string '(("ru" "Полировать")   ("uk" "Полірувати")     ("en" "Polish")) "Polish")
                          (utils-locale-string '(("ru" "Хонинговать")  ("uk" "Хонінгувати")    ("en" "Hone"))   "Hone")
                          (utils-locale-string '(("ru" "Накатать")     ("uk" "Накатувати")     ("en" "Roll"))   "Roll")))
                   (list "rb_1_osn_ml_sn" "1")        
                   (list "rb_1_osn_ml_nesn" "0")      
                   (list "rb_1_osn_ml_neobr" "0")     
                   (list "rb_1_bez_sk" "1")           
                   (list "rb_1_kr_sk" "0")            
                   (list "rb_1_kv_sk" "0")            
                   (list "tgl_1_po_konturu" "0")      
                   (list "tgl_1_perevern" "0")        
                   (list "tgl_1_napr_miko_ner" "0")
                   (list "pl_1_napr_miko_ner"
                         "0"
                         (list
                          (utils-locale-string '(("ru" "Параллельное")     ("uk" "Паралельне")      ("en" "Parallel"))      "Parallel")
                          (utils-locale-string '(("ru" "Перпендикулярное") ("uk" "Перпендикулярне") ("en" "Perpendicular")) "Perpendicular")
                          (utils-locale-string '(("ru" "Скрещенное")       ("uk" "Перехресне")      ("en" "Crossed"))       "Crossed")
                          (utils-locale-string '(("ru" "Кольчужное")       ("uk" "Кільчужне")       ("en" "Chain"))         "Chain") 
                          (utils-locale-string '(("ru" "Концентричное")    ("uk" "Концентричне")    ("en" "Concentric"))    "Concentric")
                          (utils-locale-string '(("ru" "Радиальное")       ("uk" "Радіальне")       ("en" "Radial"))        "Radial")
                          (utils-locale-string '(("ru" "Точечное")         ("uk" "Точкове")         ("en" "Spot"))          "Spot")))
                   (list "eb_1_masht" "1") 
                   (list "pl_1_masht"
                         "11"
                         (list "100:1" "50:1" "40:1" "25:1"
                               "20:1" "15:1" "10:1" "5:1" "4:1" "2.5:1" "2:1"
                               "1:1"
                               "1:2" "1:2.5" "1:4" "1:5" "1:10" "1:15"
                               "1:20" "1:25" "1:40" "1:50" "1:100")) 
                   (list "error" "")))))
  (reg_read_default_lst reg_root rou_registry)
  (if (null (tblsearch "style" "t"))
      (stl))
  (setq setup_lst (subst (list "eb_1_masht" (rtos (getvar "DIMSCALE") 2 4)) (assoc "eb_1_masht" setup_lst) setup_lst))
  (setq do_dialog t)
  (setq dcl_id
        (load_dialog
         (findfile
          (utils:path-src-lsp
           (strcat "dims/rou_1/" utils-locale "/" utils-locale "-rou_1.dcl")))))
  (while do_dialog
         (if (not (new_dialog "roughness" dcl_id "" rou_1:dia_sher_pos))
             (exit))
         (rou_1:init)
         (mapcar (function (lambda (el) (action_tile (car el) "(rou_1:ac_1)"))) setup_lst)
         (action_tile "cancel" "(setq rou_1:dia_sher_pos(done_dialog 0))")
         (action_tile "accept" "(setq rou_1:dia_sher_pos(done_dialog 1))")
         (action_tile "bt_1_1" "(setq rou_1:dia_sher_pos(done_dialog 2))")
         (action_tile "bt_1_2" "(setq rou_1:dia_sher_pos(done_dialog 3))")
         (action_tile "bt_1_3" "(setq rou_1:dia_sher_pos(done_dialog 4))")
         (action_tile "bt_1_masht" "(rou_1:ac_bt_1_masht)")
         (action_tile "rb_1_Ra" "(rou_1:ac_rb_1_Ra $value)")
         (action_tile "rb_1_Rz" "(rou_1:ac_rb_1_Rz $value)")
         (action_tile "pl_1_RaRz" "(rou_1:ac_pl_1_RaRz $value)")
         (action_tile "tgl_1_max_val" "(rou_1:ac_tgl_1_max_val $value)")
         (action_tile "tgl_1_min_val" "(rou_1:ac_tgl_1_min_val $value)")
         (action_tile "tgl_1_spos_pol" "(rou_1:ac_tgl_1_spos_pol $value)")
         (action_tile "eb_1_max_val" "(rou_1:ac_eb_1_max_val $value)")
         (action_tile "eb_1_min_val" "(rou_1:ac_eb_1_min_val $value)")
         (action_tile "eb_1_spos_pol" "(rou_1:ac_eb_1_spos_pol $value)")
         (action_tile "pl_1_max_val" "(rou_1:ac_pl_1_max_val $value)")
         (action_tile "pl_1_min_val" "(rou_1:ac_pl_1_min_val $value)")
         (action_tile "pl_1_masht" "(rou_1:ac_pl_1_masht $value)")
         (action_tile "pl_1_spos_pol" "(rou_1:ac_pl_1_spos_pol $value)")
         (action_tile "help" "(rou_1:help)")
         (setq ac (start_dialog))
         (cond ((= ac 0) (setq do_dialog nil))
               ((= ac 1) (rou_1:ac_ok))
               ((= ac 2)
                (setq p1 (getpoint
                          (utils-locale-string
                           '(("ru" "\nВерхняя точка на вертикали знака:")
                             ("uk" "\nВерхня точка на вертикалі знака:")
                             ("en" "\nTop point on the sign vertical:"))
                           "\nTop point on the sign vertical:")))
                (if p1
                    (progn (setq osm (getvar "osmode"))
                           (setvar "osmode" 128)
                           (setq p2 (getpoint p1
                                              (utils-locale-string
                                               '(("ru" "\nНижняя точка на вертикали знака:")
                                                 ("uk" "\nНижня точка на вертикалі знака:")
                                                 ("en" "\nBottom point on the sign vertical:"))
                                               "\nBottom point on the sign vertical:")))
                           (setvar "osmode" osm)))
                (if (and p1 p2)
                    (progn (rou_1:draw_sher p1 p2)
                           (setq en (entlast))
                           (command-s "_regen")
                           (setq setup_lst (subst (list "error" "")
                                                  (assoc "error" setup_lst) setup_lst)))
                    (setq setup_lst (subst
                                     (cons "error"
                                           (utils-locale-string
                                            '(("ru" "Необходимо вводить две точки !")
                                              ("uk" "Необхідно вводити дві точки !")
                                              ("en" "You must enter two points !"))
                                            "You must enter two points !"))
                                     (assoc "error" setup_lst) setup_lst))))
               ((= ac 3)
                (setq en (car
                          (entsel
                           (utils-locale-string
                            '(("ru" "\nВыберите шероховатость:")
                              ("uk" "\nВиберіть шорсткість:")
                              ("en" "\nSelect the roughness:"))
                            "\nSelect the roughness:"))))
                (if en
                    (progn
                      (setq ob      (vlax-ename->vla-object en)
                            vl-data (vlax-ldata-get ob "rou"))
                      (if (and ob vl-data)
                          (progn (setq p2
                                       (vlax-safearray->list (vlax-variant-value (vlax-get-property ob 'insertionpoint)))
                                       dp
                                       (mapcar (function -)
                                               (vlax-ldata-get ob "rou-p_top")
                                               (vlax-ldata-get ob "rou-p_bas"))
                                       p1
                                       (mapcar (function +) p2 dp)
                                       setup_lst
                                       (cond (vl-data (rou_1:update_ver_rou vl-data))
                                             ((null vl-data) setup_lst)))
                                 (command-s "_regen"))
                          (setq setup_lst
                                (subst
                                 (list "error"
                                       (utils-locale-string
                                        '(("ru" "Необходимо выбрать знак шероховатости")
                                          ("uk" "Необхідно вибрати знак шорсткості")
                                          ("en" "You must select a roughness symbol"))
                                        "You must select a roughness symbol"))
                                 (assoc "error" setup_lst) setup_lst))))
                    (setq setup_lst
                          (subst
                           (list "error"
                                 (utils-locale-string
                                  '(("ru" "Ничего не выбрано")
                                    ("uk" "Нічого не вибрано")
                                    ("en" "Nothing selected"))
                                  "Nothing selected"))
                           (assoc "error" setup_lst) setup_lst))))
               ((= ac 4)
                (if (and p1 p2)
                    (progn (entdel en)
                           (rou_1:draw_sher p1 p2)
                           (setq en (entlast))
                           (command-s "_regen")
                           (setq setup_lst
                                 (subst
                                  (list "error" "")
                                  (assoc "error" setup_lst) setup_lst)))))))
  (unload_dialog dcl_id)
  (err-handle ""))
