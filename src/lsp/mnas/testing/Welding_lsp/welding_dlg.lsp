(defun ac_accept  ()
  (setq dia_weld_pos (done_dialog 1))
  (setq reg_val (mapcar (function (lambda (el) (cons el (list (eval el)))))
                        (list 'setup_lst 'dia_weld_pos)))
  (reg_write_default_lst reg_root reg_val))

(defun ac_apply_btn () (setq dia_weld_pos (done_dialog 2)))

;;;Применяет к текущей редактируемой позиции изменения, выполненные в диалоге
(defun ac_accept_do  ()
  (mid_point_apply)
  (arrow_apply)                                                                 ;(text_top_bot_apply)
  (text_list_apply)
  (tgl_list_apply)
  (setq dim_stl_tile (assoc "dim_style" setup_lst)
        dim_stl      (nth (atoi (cadr dim_stl_tile)) (caddr dim_stl_tile))
        ed           (subst (cons 340 (TBLOBJNAME "dimstyle" dim_stl)) (assoc 340 ed) ed))
  (weld_pp_list_apply)
  (entmod ed)
  (command-s "_redraw"))

;;;Применяет к текущей редактируемой позиции изменения, выполненные в диалоге
(defun ac_apply_do  ()
  (mid_point_apply)
  (arrow_apply)
  (text_top_bot_apply)
  (text_list_apply)
  (tgl_list_apply)
  (setq dim_stl_tile (assoc "dim_style" setup_lst)
        dim_stl      (nth (atoi (cadr dim_stl_tile)) (caddr dim_stl_tile))
        ed           (subst (cons 340 (TBLOBJNAME "dimstyle" dim_stl)) (assoc 340 ed) ed))
  (weld_pp_list_apply)
  (entmod ed)
  (command-s "_redraw"))

(defun arrow_apply  ()
  (setq group_40 (assoc 40 ed)
        group_41 (assoc 41 ed)
        val_40   (cdr (assoc 40 ed))
        val_41   (cdr (assoc 41 ed)))
  (cond ((and (get_tile_test "rb_clock") (> val_40 0.0))
         (setq ed (subst_dxf (list (cons 40 (* -1. val_40)) (cons 41 (* -1. val_41))) ed)))
        ((and (get_tile_test "rb_unclock") (< val_40 0.0))
         (setq ed (subst_dxf (list (cons 40 (* -1. val_40)) (cons 41 (* -1. val_41))) ed)))))

;;;Выполняет применение операции mathprop для позиции.
(defun ac_match_apply  (/			  ;
			MATCH_PROP		  ; Набор выбора 
			MATCH_PROP_ED		  ; DXF - данные i - того элемента из набора выбора
			MATCH_PROP_EN		  ; Имя i-того элемента набора выбора
			MATCH_PROP_LENGTH	  ; Количество элементов в наборе выбора
			i			  ; Индекс для прохода по элементам набора выбора
                        )
  (setq match_prop (ssget))
  (setq	match_prop_length (sslength match_prop)
	i		  0)
  (while (< i match_prop_length)
    (setq match_prop_en	(ssname match_prop i)
	  match_prop_ed	(entget match_prop_en))
    (cond ((= "MNASPozition" (cdr (assoc 0 match_prop_ed)))
	   (if (= "1" (cadr (assoc "text_toggle" setup_lst)))
	     (progn (setq match_prop_ed (subst (assoc 1 ed) (assoc 1 match_prop_ed) match_prop_ed))))
	   (if (= "1" (cadr (assoc "arrow_type_toggle" setup_lst)))
	     (progn (setq match_prop_ed (subst (assoc 91 ed) (assoc 91 match_prop_ed) match_prop_ed))))
	   (if (= "1" (cadr (assoc "dim_style_toggle" setup_lst)))
	     (progn (setq match_prop_ed (subst (assoc 340 ed) (assoc 340 match_prop_ed) match_prop_ed))))
	   (if (= "1" (cadr (assoc "text-scale_toggle" setup_lst)))
	     (progn (setq match_prop_ed (subst (assoc 40 ed) (assoc 40 match_prop_ed) match_prop_ed))))
	   (if (= "1" (cadr (assoc "line-offset_toggle" setup_lst)))
	     (progn (setq match_prop_ed (subst (assoc 41 ed) (assoc 41 match_prop_ed) match_prop_ed))))
	   (if (= "1" (cadr (assoc "text_color_toggle" setup_lst)))
	     (progn (setq match_prop_ed (subst (assoc 70 ed) (assoc 70 match_prop_ed) match_prop_ed))))
	   (entmod match_prop_ed)))
    (setq i (1+ i)))
  (command-s "_redraw"))

(defun ac_text_color_image (key x y) (done_dialog 5))

(defun about  ()
  (alert (strcat "Редактирование обозначений сварных швов" (about-GPL-string))))

(defun litera-from-to-list  (litera from to / i lst)
  (setq i to)
  (repeat (- to from -1)
    (setq lst (cons i lst)
          i   (1- i)))
  (mapcar (function (lambda (el) (strcat litera (rtos el)))) lst))

(defun slide_setup  ()
  (mapcar (function slide_show)
          '("img_katet"             "img_close_contur"      "img_open_contur"
            "img_usilenie_top"      "img_plavn_top"         "img_montaz"
            "img_usilenie_bot"      "img_plavn_bot")))

(defun slide_show  (img_name)
  (start_image img_name)
  (setq	dx (dimx_tile img_name)
	dy (dimy_tile img_name))
  (fill_image 0 0 dx dy 0)
  (slide_image
    0
    0
    dx
    dy
    (findfile (utils:path-src-lsp (strcat "mnas/testing/Welding_lsp" "/" img_name "." "sld"))))
  (end_image))

(defun text_setup  (title dxf_code)
  (setq setup_lst (subst (list title (cdr (assoc dxf_code ed))) (assoc title setup_lst) setup_lst)))

(defun text_apply  (title dxf_code)
  (setq ed (subst (cons dxf_code (cadr (assoc title setup_lst))) (assoc dxf_code ed) ed)))

(defun setup_bit_mask  ()
  (setq mask_bLeftJoin 1
        mask_bUpSideDown 2
        mask_ContourClosed 4
        mask_ContourOpend 8
        mask_Montaz 16
        mask_Usilenie_Top 32
        mask_Usilenie_Bot 64
        mask_PlavnPereh_Top 128
        mask_PlavnPereh_Bot 256
        mask_DislLinear 512
        mask_DislShahm 1024
        mask_Katet 2048)
  (setq tgl_list  '("tgl_ob_side"         "tgl_katet"           "tgl_linear"
                    "tgl_shahm"           "tgl_close_contur"    "tgl_open_contur"
                    "tgl_usilenie_top"    "tgl_plavn_top"       "tgl_montaz"
                    "tgl_usilenie_bot"    "tgl_plavn_bot")
        mask_list (list mask_bUpSideDown        mask_Katet              mask_DislLinear
                        mask_DislShahm          mask_ContourClosed      mask_ContourOpend
                        mask_Usilenie_Top       mask_PlavnPereh_Top     mask_Montaz
                        mask_Usilenie_Bot       mask_PlavnPereh_Bot)))

(defun bit_string  (title bit_mask)
  (list title
        (cond ((/= 0 (logand bits bit_mask)) "1")
              (t "0"))))

(defun setup_tgl  (/ bits)
  (setq bits (cdr (assoc 91 ed)))
  (setq setup_lst (subst_dxf (mapcar (function bit_string) tgl_list mask_list) setup_lst))
  (if (/= 0 (logand bits mask_bleftjoin))
    (setq setup_lst (subst_dxf '(("rb_prisoed_left" "1") ("rb_prisoed_right" "0")) setup_lst))
    (setq setup_lst (subst_dxf '(("rb_prisoed_left" "0") ("rb_prisoed_right" "1")) setup_lst))))

(defun text_list_apply  ()
  (mapcar (function text_apply)
          '("top_text" "bot_text" "str_katet" "str_provar" "str_provar_neprovar")
          '(300 301 302 303 304)))

(defun tgl_list_apply  (/ rez)
  (setq rez (apply (function +) (mapcar (function tgl_apply) tgl_list mask_list))
        rez (+ rez (atoi (cadr (assoc "rb_prisoed_left" setup_lst))))
        ed  (subst (cons 91 rez) (assoc 91 ed) ed)))

(defun tgl_apply  (title mask)
  (cond ((= "1" (cadr (assoc title setup_lst))) mask)
        (t 0)))

;;;"dim_style"


(defun weld_pp_list_elem  (title code / title_data code_val)
  (setq title_data (assoc title setup_lst)
        code_val   (itoa (cdr (assoc code ed))))
  (list title code_val (caddr title_data)))

(defun setup_weld_pp_list  ()
  (setq setup_lst
         (subst_dxf (mapcar (function weld_pp_list_elem) weld_pp_list_str weld_pp_list_code)
                    setup_lst)))

(defun weld_pp_list_elem_apply  (title code / title_lst)
  (setq title_lst (assoc title setup_lst)
        ed        (subst (cons code (atoi (cadr title_lst))) (assoc code ed) ed)))



(defun weld_pp_list_apply  ()
  (mapcar (function weld_pp_list_elem_apply) weld_pp_list_str weld_pp_list_code))

(defun action_tgl_close_contur  ()
  (if (= (get_tile "tgl_close_contur") "1")
    (set_tile "tgl_open_contur" "0"))
  (save_setup_list))

(defun action_tgl_open_contur  ()
  (if (= (get_tile "tgl_open_contur") "1")
    (set_tile "tgl_close_contur" "0"))
  (save_setup_list))

(defun action_tgl_usilenie_top  ()
  (if (= (get_tile "tgl_usilenie_top") "1")
    (set_tile "tgl_plavn_top" "0"))
  (save_setup_list))

(defun action_tgl_plavn_top  ()
  (if (= (get_tile "tgl_plavn_top") "1")
    (set_tile "tgl_usilenie_top" "0"))
  (save_setup_list))


(defun action_tgl_usilenie_bot  ()
  (if (= (get_tile "tgl_usilenie_bot") "1")
    (set_tile "tgl_plavn_bot" "0"))
  (save_setup_list))


(defun action_tgl_plavn_bot  ()
  (if (= (get_tile "tgl_plavn_bot") "1")
    (set_tile "tgl_usilenie_bot" "0"))
  (save_setup_list))

(defun action_tgl_linear  ()
  (if (= (get_tile "tgl_linear") "1")
    (set_tile "tgl_shahm" "0"))
  (tile_modes_set)
  (save_setup_list))

(defun tile_modes_set  ()
  (if (and (= (get_tile "tgl_linear") "0") (= (get_tile "tgl_shahm") "0"))
    (progn (mode_tile "str_provar" 1) (mode_tile "str_provar_neprovar" 1))
    (progn (mode_tile "str_provar" 0) (mode_tile "str_provar_neprovar" 0)))
  (if (= (get_tile "tgl_katet") "0")
    (mode_tile "str_katet" 1)
    (mode_tile "str_katet" 0)))

(defun action_tgl_shahm  ()
  (if (= (get_tile "tgl_shahm") "1")
    (set_tile "tgl_linear" "0"))
  (tile_modes_set)
  (save_setup_list))

(defun action_tgl_katet () (tile_modes_set) (save_setup_list))

(defun action_text_home  ()
  (setq ed (subst_dxf '((14 0.0 1.0 0.0) (15 0.0 1.0 0.0)) ed)))


(defun save_setup_list  ()
  (setq setup_lst
         (mapcar
           (function
             (lambda (el)
               (cond ((= 2 (length el)) (list (car el) (get_tile (car el))))
                     ((= 3 (length el)) (list (car el) (get_tile (car el)) (caddr el))))))
           setup_lst)))

(defun text_top_bot_apply  (/ new_text_bot new_text_top)
  (setq new_text_top (strcat (get_tile_list tile_wedl_standard)
                             "-"
                             (get_tile_list tile_weld_type)
                             "-"
                             (get_tile_list tile_weld_sposob))
        new_text_bot (strcat (get_tile_list tile_weld_kategory)
                             "-"
                             (get_tile_list tile_weld_kontrol_group)))
  (if (get_tile_test "tgl_katet")
    (setq new_text_top (strcat new_text_top "-&p" (get_tile_str "str_katet"))))
  (if (get_tile_test "tgl_linear")
    (setq new_text_top (strcat new_text_top
                               "-"
                               (get_tile_str "str_provar")
                               "/"
                               (get_tile_str "str_provar_neprovar"))))
  (if (get_tile_test "tgl_shahm")
    (setq new_text_top (strcat new_text_top
                               "-"
                               (get_tile_str "str_provar")
                               "Z"
                               (get_tile_str "str_provar_neprovar"))))
  (cond ((get_tile_test "tgl_ob_side")
         (if (get_tile_test "tgl_usilenie_top")
           (setq new_text_top (strcat new_text_top " &r")))
         (if (get_tile_test "tgl_plavn_top")
           (setq new_text_top (strcat new_text_top " &t")))
         (if (get_tile_test "tgl_usilenie_bot")
           (setq new_text_bot (strcat new_text_bot " &q")))
         (if (get_tile_test "tgl_plavn_bot")
           (setq new_text_bot (strcat new_text_bot " &s"))))
        (t
         (if (get_tile_test "tgl_open_contur")
           (setq new_text_top (strcat new_text_top " &u")))
         (if (get_tile_test "tgl_usilenie_top")
           (setq new_text_top (strcat new_text_top " &q")))
         (if (get_tile_test "tgl_plavn_top")
           (setq new_text_top (strcat new_text_top " &s")))
         (if (get_tile_test "tgl_usilenie_bot")
           (setq new_text_bot (strcat new_text_bot " &r")))
         (if (get_tile_test "tgl_plavn_bot")
           (setq new_text_bot (strcat new_text_bot " &t")))))
  (setq
    setup_lst (subst_dxf (list (list "top_text" new_text_top) (list "bot_text" new_text_bot))
                         setup_lst)))



(defun get_tile_list  (key / key_tile)
  (setq key_tile (assoc key setup_lst))
  (nth (atoi (cadr key_tile)) (caddr key_tile)))

(defun get_tile_str (key) (cadr (assoc key setup_lst)))

(defun get_tile_test  (key)
  (cond ((= "1" (cadr (assoc key setup_lst))) t)
        (t nil)))

(defun mid_point_apply  ()
  (setq p0    (cdr (assoc 10 ed))
        p1    (if (get_tile_test "rb_prisoed_left")
                (cdr (assoc 12 ed))
                (cdr (assoc 13 ed)))
        p_mid (mapcar (function (lambda (el) (* 0.5 el))) (mapcar (function +) p0 p1))
        ed    (subst_dxf (list (cons 11 p_mid)) ed)))


(defun action_wedl_standard  (/ wt_str)
  (setq wt_str (w_type_string))
  ;; Запоминаем строку, которая была.
  (setq setup_lst
         (subst_dxf
           (list (list tile_wedl_standard wst (caddr (assoc tile_wedl_standard setup_lst)))
                 ;;(list tile_weld_type "0" (eval (read (strcat "weld_type_" wst))))
                 (w_type_nomber-by-string wt_str wst))
           setup_lst)))

;;;Возвращает строку с типом сварного соединения.
;;;setup_lst - глобальная переменная содержащая список настройки диалога.
(defun w_type_string  (/ w_tyle_lst w_type w_type_no)
  (setq w_type     (assoc tile_weld_type setup_lst)
        w_type_no  (read (cadr w_type))
        w_tyle_lst (caddr w_type))
  (nth w_type_no w_tyle_lst))

;;;wst - глобальная переменная, содержащая строку "0" "1" "2" и т.д.
(defun w_type_nomber-by-string  (str wst / len_curr len_full no_curr w_tyle_lst)
  (setq w_tyle_lst (eval (read (strcat "weld_type_" wst)))
        len_curr   (length (MEMBER str w_tyle_lst))
        len_full   (length w_tyle_lst)
        no_curr    (- len_full len_curr))
  (list tile_weld_type (itoa no_curr) (eval (read (strcat "weld_type_" wst)))))

(defun get_data  (ed)
  ;; Выбор из данных примитива сварки имени размерного стиля к которому он относится
  ;; и формарование даннных для отображения диалога по ключу "dim_style".
  (setq ;; Выборка из текущего рисунка имен всех размерных стилей.
        dim_stl_lst (search_table "DIMSTYLE")
        ;; Выборка из данных примитива сварного шва имени размерного стиля к которому он относится.
        dim_stl     (cdr (assoc 3 ed))	;(cdr (assoc 2 (entget (cdr (assoc 3 ed)))))
        ;; Определение номера размерного стиля примитива сварки в списке имен всех размерных стилей,
        ;; имеющихся в текущем рисунке.
        dim_stl_n   (- (length dim_stl_lst) (length (member dim_stl dim_stl_lst)))
        ;; Формирование данных, относящихся к размерному стилю примитива, для отображения диалога.
        setup_lst   (subst (list "dim_style" (rtos dim_stl_n) dim_stl_lst)
                           (assoc "dim_style" setup_lst)
                           setup_lst))
  ;; Выборка из данных примитива сварки информации о расположении относительно линии выноски и
  ;; формирование данных для отображения диалога по ключам "rb_clock" "rb_unclock".
  (if (< (cdr (assoc 40 ed)) 0)
    (setq setup_lst (subst_dxf (list (list "rb_clock" "1") (list "rb_unclock" "0")) setup_lst))
    (setq setup_lst (subst_dxf (list (list "rb_clock" "0") (list "rb_unclock" "1")) setup_lst)))
  ;; Выборка из данных примитива сварки информации о строковых параметрах и
  ;; формирование данных, используемых для отображения диалога.
  (mapcar (function text_setup)
          '("top_text" "bot_text" "str_katet" "str_provar" "str_provar_neprovar")
          '(300 301 302 303 304))
  ;; Выборка из данных примитива сварки информации о стадарте, типе, способе сварки,
  ;; категории и комплексе сварного шва и
  ;; формирование данных для отображения диалога.
  ;; (setup_weld_pp_list) ; Здесь ошибка
  ;; Выборка из данных примитива сварки информации о битовой маске и
  ;; формирование данных для отображения диалога.
  ;; (setup_tgl); 
  )

;; Выбор сварного шва.
(defun select  (/ en)
  (setq en (car (entsel "\nВыберите сварной шов:"))
        ed (entget en))
  (check_type))

(defun check_type  ()
  (if (/= (cdr (assoc 0 ed)) "LEADER")
    (progn (alert "Выбранный вами объект не соответствует типу LEADER.") (exit))))
