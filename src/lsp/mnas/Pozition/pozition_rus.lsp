(setq *position-command-list* '("pos_export" "pozition_set_text_scale" "edpos" "ep"))
;;;; (opech_cmds-str *position-command-list*)

(defun c:ηωϋ_σχηωκε() (c:pos_export))
(defun c:ηω�ψεψως_ϋσε_εσχε_ϋρτδσ() (c:pozition_set_text_scale))
(defun c:σβηωϋ() (c:edpos))
(defun c:ση() (c:ep))

(princ "Loaded project position.\n")
