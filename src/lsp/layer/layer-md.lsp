;;;;;;("ml_off"
;;;;;;"Выключает слои со вспомогательными элементами,\n заканчивающимися на \"*work\"." "Слои")
(defun c:ml_off  ()
  (err-init '("cmdecho"))
  (set-sys-var-lst '(("cmdecho" 0)))
  (command-s "-layer" "off" "*work")
  (if_cmd_active)
  (err-handle ""))

;;;;;;("ml_on"
;;;;;;  "Включает слои со вспомогательными элементами,\n заканчивающимися на \"*work\"." "Слои")
(defun c:ml_on  ()
  (err-init '("cmdecho"))
  (set-sys-var-lst '(("cmdecho" 0)))
  (command-s "-layer" "_on" "*work")
  (if_cmd_active)
  (err-handle ""))

;;;;;;("ml_on_c" "not defined" "Слои")
(defun c:ml_on_c  (/ ed la_name)
  (err-init '("cmdecho"))
  (set-sys-var-lst '(("cmdecho" 0)))
  (setq ed      (entget (car (entsel "\nВыберите примитив:")))
        la_name (cdr (assoc 2 ed)))
  (command-s "-_layer" "_on" (strcat "*" la_name "*work") "")
  (err-handle ""))

;;;;;;("ml_off_c" "not defined" "Слои")
(defun c:ml_off_c  (/ ed la_name)
  (err-init '("cmdecho"))
  (set-sys-var-lst '(("cmdecho" 0)))
  (setq ed      (entget (car (entsel "\nВыберите примитив:")))
        la_name (cdr (assoc 2 ed)))
  (command-s "-_layer" "_off" (strcat "*" la_name "*work") "")
  (err-handle ""))

;;;;;;("am_la" "not defined" "Слои")
(defun c:am_la  ()
  (err-init '("cmdecho"))
  (set-sys-var-lst '(("cmdecho" 0)))
  (command-s "-_layer" "_color" 7 "am_7,am_4,am_pardim" "")
  (err-handle ""))
