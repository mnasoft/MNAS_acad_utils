(defun c:foo (/ en file i ss ss_len)
  (setq	ss     (ssget "X" '((0 . "DIMENSION")))
	ss_len (sslength ss)
	i      0
  )
  (setq file (open "d:/dop_list.lsp" "a"))
  (while (< i ss_len)
    (setq en (ssname ss i))
    (foo en)
    (setq i (1+ i))
  )
  (close file)
)


(defun foo (en	       /	  dist	     ed		p0
	    p1	       pos_dop_end	     pos_dop_start
	    pos_end    pos_mid	  pos_start  str_1	str_dop
	    str_low    str_up	  text
	   )
  (setq
    ed		  (entget en)
    p0		  (cdr (assoc 13 ed))
    p1		  (cdr (assoc 14 ed))
    dist	  (distance p0 p1)
    text	  (cdr (assoc 1 ed))
    pos_dop_start (1+ (vl-string-search " " text))
    pos_dop_end	  (1+ (vl-string-search "\\C92" text))
    str_dop	  (substr text
			  (1+ pos_dop_start)
			  (- pos_dop_end (1+ pos_dop_start))
		  )
    pos_start	  (1+ (vl-string-search "\\S" text))
    str_1	  (substr text pos_start)
    pos_mid	  (1+ (vl-string-search "^" str_1))
    str_up	  (substr str_1 3 (- pos_mid 3))
    pos_end	  (1+ (vl-string-search ";" str_1))
    str_low	  (substr str_1 (1+ pos_mid) (- pos_end (1+ pos_mid)))
  )
;;;  (princ dist)
;;;  (princ " ")
;;;  (princ str_dop)
;;;  (princ " ")
;;;  (princ str_up)
;;;  (princ " ")
;;;  (princ str_low)
;;;  (princ)
  (print (list dist str_dop (atof str_up) (atof str_low))
	 file
  )
)




(mapcar
  (function
    (lambda (litera)
      (mapcar
	(function
	  (lambda (dopu)
	    (princ (strcat "proc(\"" litera dopu "\");\n")
	    )
	  )
	)
	'("18"	"17"  "16"  "15"  "14"	"13"  "12"  "11"  "10"	"9"
	  "8"	"7"   "6"   "5"	  "4"	"3"   "2"   "1"	  "0"	"01"
	 )
      )
    )
  )
  '("a"	  "b"	"c"   "cd"  "d"	  "e"	"ef"  "f"   "fg"  "g"	"h"
    "j"	  "js"	"k"   "l"   "m"	  "n"	"p"   "r"   "s"	  "t"	"u"
    "v"	  "x"	"y"   "z"   "za"  "zb"	"zc"
    "A"	  "B"	"C"   "CD"  "D"	  "E"	"EF"  "F"   "FG"  "G"	"H"
    "J"	  "JS"	"K"   "L"   "M"	  "N"	"P"   "R"   "S"	  "T"	"U"
    "V"	  "X"	"Y"   "Z"   "ZA"  "ZB"	"ZC"
   )
)

(mapcar
  (function
    (lambda (litera)
      (mapcar
	(function
	  (lambda (dopu)
	    (princ (strcat "proc(\"" litera dopu "\");\n"))
	    (list(strcat litera dopu))
	  )
	)
	'("18"	"17"  "16"  "15"  "14"	"13"  "12"  "11"  "10"	"9"
	  "8"	"7"   "6"   "5"	  "4"	"3"   "2"   "1"	  "0"	"01"
	 )
      )
    )
  )
  '("a"	  "b"	"c"   "cd"  "d"	  "e"	"ef"  "f"   "fg"  "g"	"h"
    "j"	  "js"	"k"   "l"   "m"	  "n"	"p"   "r"   "s"	  "t"	"u"
    "v"	  "x"	"y"   "z"   "za"  "zb"	"zc"
    "A"	  "B"	"C"   "CD"  "D"	  "E"	"EF"  "F"   "FG"  "G"	"H"
    "J"	  "JS"	"K"   "L"   "M"	  "N"	"P"   "R"   "S"	  "T"	"U"
    "V"	  "X"	"Y"   "Z"   "ZA"  "ZB"	"ZC"
   )
)

(setq
  lst_dist_interval
   (mapcar
     (function
       (lambda (el1 el2)
	 (list el2 (car el1) (cadr el1))
       )
     )
     '((0.0 3.0)
       (3.0 6.0)
       (6.0 10.0)
       (10.0 14.0)
       (14.0 18.0)
       (18.0 24.0)
       (24.0 30.0)
       (30.0 40.0)
       (40.0 50.0)
       (50.0 65.0)
       (65.0 80.0)
       (80.0 100.0)
       (100.0 120.0)
       (120.0 140.0)
       (140.0 160.0)
       (160.0 180.0)
       (180.0 200.0)
       (200.0 225.0)
       (225.0 250.0)
       (250.0 280.0)
       (280.0 315.0)
       (315.0 355.0)
       (355.0 400.0)
       (400.0 450.0)
       (450.0 500.0)
       (500.0 560.0)
       (560.0 630.0)
       (630.0 710.0)
       (710.0 800.0)
       (800.0 900.0)
       (900.0 1000.0)
       (1000.0 1120.0)
       (1120.0 1250.0)
       (1250.0 1400.0)
       (1400.0 1600.0)
       (1600.0 1800.0)
       (1800.0 2000.0)
       (2000.0 2240.0)
       (2240.0 2500.0)
       (2500.0 2800.0)
       (2800.0 3150.0)
      )
     (reverse '(2975.0	2650.0	2370.0	2120.0	1900.0	1700.0	1500.0
		1325.0	1185.0	1060.0	950.0	850.0	755.0	670.0
		595.0	530.0	470.0	420.0	377.5	335.0	297.5
		265.0	237.5	212.5	190.0	170.0	150.0	130.0
		110.0	90.0	72.5	57.5	45.0	35.0	27.0
		21.0	16.0	12.0	8.0	4.5	1.5
	       )
     )
   )
)

(setq
  kvalitet_name_lst
   '(("a18")
     ("a17")
     ("a16")
     ("a15")
     ("a14")
     ("a13")
     ("a12")
     ("a11")
     ("a10")
     ("a9")
     ("a8")
     ("a7")
     ("a6")
     ("a5")
     ("a4")
     ("a3")
     ("a2")
     ("a1")
     ("a0")
     ("a01")
     ("b18")
     ("b17")
     ("b16")
     ("b15")
     ("b14")
     ("b13")
     ("b12")
     ("b11")
     ("b10")
     ("b9")
     ("b8")
     ("b7")
     ("b6")
     ("b5")
     ("b4")
     ("b3")
     ("b2")
     ("b1")
     ("b0")
     ("b01")
     ("c18")
     ("c17")
     ("c16")
     ("c15")
     ("c14")
     ("c13")
     ("c12")
     ("c11")
     ("c10")
     ("c9")
     ("c8")
     ("c7")
     ("c6")
     ("c5")
     ("c4")
     ("c3")
     ("c2")
     ("c1")
     ("c0")
     ("c01")
     ("cd18")
     ("cd17")
     ("cd16")
     ("cd15")
     ("cd14")
     ("cd13")
     ("cd12")
     ("cd11")
     ("cd10")
     ("cd9")
     ("cd8")
     ("cd7")
     ("cd6")
     ("cd5")
     ("cd4")
     ("cd3")
     ("cd2")
     ("cd1")
     ("cd0")
     ("cd01")
     ("d18")
     ("d17")
     ("d16")
     ("d15")
     ("d14")
     ("d13")
     ("d12")
     ("d11")
     ("d10")
     ("d9")
     ("d8")
     ("d7")
     ("d6")
     ("d5")
     ("d4")
     ("d3")
     ("d2")
     ("d1")
     ("d0")
     ("d01")
     ("e18")
     ("e17")
     ("e16")
     ("e15")
     ("e14")
     ("e13")
     ("e12")
     ("e11")
     ("e10")
     ("e9")
     ("e8")
     ("e7")
     ("e6")
     ("e5")
     ("e4")
     ("e3")
     ("e2")
     ("e1")
     ("e0")
     ("e01")
     ("ef18")
     ("ef17")
     ("ef16")
     ("ef15")
     ("ef14")
     ("ef13")
     ("ef12")
     ("ef11")
     ("ef10")
     ("ef9")
     ("ef8")
     ("ef7")
     ("ef6")
     ("ef5")
     ("ef4")
     ("ef3")
     ("ef2")
     ("ef1")
     ("ef0")
     ("ef01")
     ("f18")
     ("f17")
     ("f16")
     ("f15")
     ("f14")
     ("f13")
     ("f12")
     ("f11")
     ("f10")
     ("f9")
     ("f8")
     ("f7")
     ("f6")
     ("f5")
     ("f4")
     ("f3")
     ("f2")
     ("f1")
     ("f0")
     ("f01")
     ("fg18")
     ("fg17")
     ("fg16")
     ("fg15")
     ("fg14")
     ("fg13")
     ("fg12")
     ("fg11")
     ("fg10")
     ("fg9")
     ("fg8")
     ("fg7")
     ("fg6")
     ("fg5")
     ("fg4")
     ("fg3")
     ("fg2")
     ("fg1")
     ("fg0")
     ("fg01")
     ("g18")
     ("g17")
     ("g16")
     ("g15")
     ("g14")
     ("g13")
     ("g12")
     ("g11")
     ("g10")
     ("g9")
     ("g8")
     ("g7")
     ("g6")
     ("g5")
     ("g4")
     ("g3")
     ("g2")
     ("g1")
     ("g0")
     ("g01")
     ("h18")
     ("h17")
     ("h16")
     ("h15")
     ("h14")
     ("h13")
     ("h12")
     ("h11")
     ("h10")
     ("h9")
     ("h8")
     ("h7")
     ("h6")
     ("h5")
     ("h4")
     ("h3")
     ("h2")
     ("h1")
     ("h0")
     ("h01")
     ("j18")
     ("j17")
     ("j16")
     ("j15")
     ("j14")
     ("j13")
     ("j12")
     ("j11")
     ("j10")
     ("j9")
     ("j8")
     ("j7")
     ("j6")
     ("j5")
     ("j4")
     ("j3")
     ("j2")
     ("j1")
     ("j0")
     ("j01")
     ("js18")
     ("js17")
     ("js16")
     ("js15")
     ("js14")
     ("js13")
     ("js12")
     ("js11")
     ("js10")
     ("js9")
     ("js8")
     ("js7")
     ("js6")
     ("js5")
     ("js4")
     ("js3")
     ("js2")
     ("js1")
     ("js0")
     ("js01")
     ("k18")
     ("k17")
     ("k16")
     ("k15")
     ("k14")
     ("k13")
     ("k12")
     ("k11")
     ("k10")
     ("k9")
     ("k8")
     ("k7")
     ("k6")
     ("k5")
     ("k4")
     ("k3")
     ("k2")
     ("k1")
     ("k0")
     ("k01")
     ("l18")
     ("l17")
     ("l16")
     ("l15")
     ("l14")
     ("l13")
     ("l12")
     ("l11")
     ("l10")
     ("l9")
     ("l8")
     ("l7")
     ("l6")
     ("l5")
     ("l4")
     ("l3")
     ("l2")
     ("l1")
     ("l0")
     ("l01")
     ("m18")
     ("m17")
     ("m16")
     ("m15")
     ("m14")
     ("m13")
     ("m12")
     ("m11")
     ("m10")
     ("m9")
     ("m8")
     ("m7")
     ("m6")
     ("m5")
     ("m4")
     ("m3")
     ("m2")
     ("m1")
     ("m0")
     ("m01")
     ("n18")
     ("n17")
     ("n16")
     ("n15")
     ("n14")
     ("n13")
     ("n12")
     ("n11")
     ("n10")
     ("n9")
     ("n8")
     ("n7")
     ("n6")
     ("n5")
     ("n4")
     ("n3")
     ("n2")
     ("n1")
     ("n0")
     ("n01")
     ("p18")
     ("p17")
     ("p16")
     ("p15")
     ("p14")
     ("p13")
     ("p12")
     ("p11")
     ("p10")
     ("p9")
     ("p8")
     ("p7")
     ("p6")
     ("p5")
     ("p4")
     ("p3")
     ("p2")
     ("p1")
     ("p0")
     ("p01")
     ("r18")
     ("r17")
     ("r16")
     ("r15")
     ("r14")
     ("r13")
     ("r12")
     ("r11")
     ("r10")
     ("r9")
     ("r8")
     ("r7")
     ("r6")
     ("r5")
     ("r4")
     ("r3")
     ("r2")
     ("r1")
     ("r0")
     ("r01")
     ("s18")
     ("s17")
     ("s16")
     ("s15")
     ("s14")
     ("s13")
     ("s12")
     ("s11")
     ("s10")
     ("s9")
     ("s8")
     ("s7")
     ("s6")
     ("s5")
     ("s4")
     ("s3")
     ("s2")
     ("s1")
     ("s0")
     ("s01")
     ("t18")
     ("t17")
     ("t16")
     ("t15")
     ("t14")
     ("t13")
     ("t12")
     ("t11")
     ("t10")
     ("t9")
     ("t8")
     ("t7")
     ("t6")
     ("t5")
     ("t4")
     ("t3")
     ("t2")
     ("t1")
     ("t0")
     ("t01")
     ("u18")
     ("u17")
     ("u16")
     ("u15")
     ("u14")
     ("u13")
     ("u12")
     ("u11")
     ("u10")
     ("u9")
     ("u8")
     ("u7")
     ("u6")
     ("u5")
     ("u4")
     ("u3")
     ("u2")
     ("u1")
     ("u0")
     ("u01")
     ("v18")
     ("v17")
     ("v16")
     ("v15")
     ("v14")
     ("v13")
     ("v12")
     ("v11")
     ("v10")
     ("v9")
     ("v8")
     ("v7")
     ("v6")
     ("v5")
     ("v4")
     ("v3")
     ("v2")
     ("v1")
     ("v0")
     ("v01")
     ("x18")
     ("x17")
     ("x16")
     ("x15")
     ("x14")
     ("x13")
     ("x12")
     ("x11")
     ("x10")
     ("x9")
     ("x8")
     ("x7")
     ("x6")
     ("x5")
     ("x4")
     ("x3")
     ("x2")
     ("x1")
     ("x0")
     ("x01")
     ("y18")
     ("y17")
     ("y16")
     ("y15")
     ("y14")
     ("y13")
     ("y12")
     ("y11")
     ("y10")
     ("y9")
     ("y8")
     ("y7")
     ("y6")
     ("y5")
     ("y4")
     ("y3")
     ("y2")
     ("y1")
     ("y0")
     ("y01")
     ("z18")
     ("z17")
     ("z16")
     ("z15")
     ("z14")
     ("z13")
     ("z12")
     ("z11")
     ("z10")
     ("z9")
     ("z8")
     ("z7")
     ("z6")
     ("z5")
     ("z4")
     ("z3")
     ("z2")
     ("z1")
     ("z0")
     ("z01")
     ("za18")
     ("za17")
     ("za16")
     ("za15")
     ("za14")
     ("za13")
     ("za12")
     ("za11")
     ("za10")
     ("za9")
     ("za8")
     ("za7")
     ("za6")
     ("za5")
     ("za4")
     ("za3")
     ("za2")
     ("za1")
     ("za0")
     ("za01")
     ("zb18")
     ("zb17")
     ("zb16")
     ("zb15")
     ("zb14")
     ("zb13")
     ("zb12")
     ("zb11")
     ("zb10")
     ("zb9")
     ("zb8")
     ("zb7")
     ("zb6")
     ("zb5")
     ("zb4")
     ("zb3")
     ("zb2")
     ("zb1")
     ("zb0")
     ("zb01")
     ("zc18")
     ("zc17")
     ("zc16")
     ("zc15")
     ("zc14")
     ("zc13")
     ("zc12")
     ("zc11")
     ("zc10")
     ("zc9")
     ("zc8")
     ("zc7")
     ("zc6")
     ("zc5")
     ("zc4")
     ("zc3")
     ("zc2")
     ("zc1")
     ("zc0")
     ("zc01")
     ("A18")
     ("A17")
     ("A16")
     ("A15")
     ("A14")
     ("A13")
     ("A12")
     ("A11")
     ("A10")
     ("A9")
     ("A8")
     ("A7")
     ("A6")
     ("A5")
     ("A4")
     ("A3")
     ("A2")
     ("A1")
     ("A0")
     ("A01")
     ("B18")
     ("B17")
     ("B16")
     ("B15")
     ("B14")
     ("B13")
     ("B12")
     ("B11")
     ("B10")
     ("B9")
     ("B8")
     ("B7")
     ("B6")
     ("B5")
     ("B4")
     ("B3")
     ("B2")
     ("B1")
     ("B0")
     ("B01")
     ("C18")
     ("C17")
     ("C16")
     ("C15")
     ("C14")
     ("C13")
     ("C12")
     ("C11")
     ("C10")
     ("C9")
     ("C8")
     ("C7")
     ("C6")
     ("C5")
     ("C4")
     ("C3")
     ("C2")
     ("C1")
     ("C0")
     ("C01")
     ("CD18")
     ("CD17")
     ("CD16")
     ("CD15")
     ("CD14")
     ("CD13")
     ("CD12")
     ("CD11")
     ("CD10")
     ("CD9")
     ("CD8")
     ("CD7")
     ("CD6")
     ("CD5")
     ("CD4")
     ("CD3")
     ("CD2")
     ("CD1")
     ("CD0")
     ("CD01")
     ("D18")
     ("D17")
     ("D16")
     ("D15")
     ("D14")
     ("D13")
     ("D12")
     ("D11")
     ("D10")
     ("D9")
     ("D8")
     ("D7")
     ("D6")
     ("D5")
     ("D4")
     ("D3")
     ("D2")
     ("D1")
     ("D0")
     ("D01")
     ("E18")
     ("E17")
     ("E16")
     ("E15")
     ("E14")
     ("E13")
     ("E12")
     ("E11")
     ("E10")
     ("E9")
     ("E8")
     ("E7")
     ("E6")
     ("E5")
     ("E4")
     ("E3")
     ("E2")
     ("E1")
     ("E0")
     ("E01")
     ("EF18")
     ("EF17")
     ("EF16")
     ("EF15")
     ("EF14")
     ("EF13")
     ("EF12")
     ("EF11")
     ("EF10")
     ("EF9")
     ("EF8")
     ("EF7")
     ("EF6")
     ("EF5")
     ("EF4")
     ("EF3")
     ("EF2")
     ("EF1")
     ("EF0")
     ("EF01")
     ("F18")
     ("F17")
     ("F16")
     ("F15")
     ("F14")
     ("F13")
     ("F12")
     ("F11")
     ("F10")
     ("F9")
     ("F8")
     ("F7")
     ("F6")
     ("F5")
     ("F4")
     ("F3")
     ("F2")
     ("F1")
     ("F0")
     ("F01")
     ("FG18")
     ("FG17")
     ("FG16")
     ("FG15")
     ("FG14")
     ("FG13")
     ("FG12")
     ("FG11")
     ("FG10")
     ("FG9")
     ("FG8")
     ("FG7")
     ("FG6")
     ("FG5")
     ("FG4")
     ("FG3")
     ("FG2")
     ("FG1")
     ("FG0")
     ("FG01")
     ("G18")
     ("G17")
     ("G16")
     ("G15")
     ("G14")
     ("G13")
     ("G12")
     ("G11")
     ("G10")
     ("G9")
     ("G8")
     ("G7")
     ("G6")
     ("G5")
     ("G4")
     ("G3")
     ("G2")
     ("G1")
     ("G0")
     ("G01")
     ("H18")
     ("H17")
     ("H16")
     ("H15")
     ("H14")
     ("H13")
     ("H12")
     ("H11")
     ("H10")
     ("H9")
     ("H8")
     ("H7")
     ("H6")
     ("H5")
     ("H4")
     ("H3")
     ("H2")
     ("H1")
     ("H0")
     ("H01")
     ("J18")
     ("J17")
     ("J16")
     ("J15")
     ("J14")
     ("J13")
     ("J12")
     ("J11")
     ("J10")
     ("J9")
     ("J8")
     ("J7")
     ("J6")
     ("J5")
     ("J4")
     ("J3")
     ("J2")
     ("J1")
     ("J0")
     ("J01")
     ("JS18")
     ("JS17")
     ("JS16")
     ("JS15")
     ("JS14")
     ("JS13")
     ("JS12")
     ("JS11")
     ("JS10")
     ("JS9")
     ("JS8")
     ("JS7")
     ("JS6")
     ("JS5")
     ("JS4")
     ("JS3")
     ("JS2")
     ("JS1")
     ("JS0")
     ("JS01")
     ("K18")
     ("K17")
     ("K16")
     ("K15")
     ("K14")
     ("K13")
     ("K12")
     ("K11")
     ("K10")
     ("K9")
     ("K8")
     ("K7")
     ("K6")
     ("K5")
     ("K4")
     ("K3")
     ("K2")
     ("K1")
     ("K0")
     ("K01")
     ("L18")
     ("L17")
     ("L16")
     ("L15")
     ("L14")
     ("L13")
     ("L12")
     ("L11")
     ("L10")
     ("L9")
     ("L8")
     ("L7")
     ("L6")
     ("L5")
     ("L4")
     ("L3")
     ("L2")
     ("L1")
     ("L0")
     ("L01")
     ("M18")
     ("M17")
     ("M16")
     ("M15")
     ("M14")
     ("M13")
     ("M12")
     ("M11")
     ("M10")
     ("M9")
     ("M8")
     ("M7")
     ("M6")
     ("M5")
     ("M4")
     ("M3")
     ("M2")
     ("M1")
     ("M0")
     ("M01")
     ("N18")
     ("N17")
     ("N16")
     ("N15")
     ("N14")
     ("N13")
     ("N12")
     ("N11")
     ("N10")
     ("N9")
     ("N8")
     ("N7")
     ("N6")
     ("N5")
     ("N4")
     ("N3")
     ("N2")
     ("N1")
     ("N0")
     ("N01")
     ("P18")
     ("P17")
     ("P16")
     ("P15")
     ("P14")
     ("P13")
     ("P12")
     ("P11")
     ("P10")
     ("P9")
     ("P8")
     ("P7")
     ("P6")
     ("P5")
     ("P4")
     ("P3")
     ("P2")
     ("P1")
     ("P0")
     ("P01")
     ("R18")
     ("R17")
     ("R16")
     ("R15")
     ("R14")
     ("R13")
     ("R12")
     ("R11")
     ("R10")
     ("R9")
     ("R8")
     ("R7")
     ("R6")
     ("R5")
     ("R4")
     ("R3")
     ("R2")
     ("R1")
     ("R0")
     ("R01")
     ("S18")
     ("S17")
     ("S16")
     ("S15")
     ("S14")
     ("S13")
     ("S12")
     ("S11")
     ("S10")
     ("S9")
     ("S8")
     ("S7")
     ("S6")
     ("S5")
     ("S4")
     ("S3")
     ("S2")
     ("S1")
     ("S0")
     ("S01")
     ("T18")
     ("T17")
     ("T16")
     ("T15")
     ("T14")
     ("T13")
     ("T12")
     ("T11")
     ("T10")
     ("T9")
     ("T8")
     ("T7")
     ("T6")
     ("T5")
     ("T4")
     ("T3")
     ("T2")
     ("T1")
     ("T0")
     ("T01")
     ("U18")
     ("U17")
     ("U16")
     ("U15")
     ("U14")
     ("U13")
     ("U12")
     ("U11")
     ("U10")
     ("U9")
     ("U8")
     ("U7")
     ("U6")
     ("U5")
     ("U4")
     ("U3")
     ("U2")
     ("U1")
     ("U0")
     ("U01")
     ("V18")
     ("V17")
     ("V16")
     ("V15")
     ("V14")
     ("V13")
     ("V12")
     ("V11")
     ("V10")
     ("V9")
     ("V8")
     ("V7")
     ("V6")
     ("V5")
     ("V4")
     ("V3")
     ("V2")
     ("V1")
     ("V0")
     ("V01")
     ("X18")
     ("X17")
     ("X16")
     ("X15")
     ("X14")
     ("X13")
     ("X12")
     ("X11")
     ("X10")
     ("X9")
     ("X8")
     ("X7")
     ("X6")
     ("X5")
     ("X4")
     ("X3")
     ("X2")
     ("X1")
     ("X0")
     ("X01")
     ("Y18")
     ("Y17")
     ("Y16")
     ("Y15")
     ("Y14")
     ("Y13")
     ("Y12")
     ("Y11")
     ("Y10")
     ("Y9")
     ("Y8")
     ("Y7")
     ("Y6")
     ("Y5")
     ("Y4")
     ("Y3")
     ("Y2")
     ("Y1")
     ("Y0")
     ("Y01")
     ("Z18")
     ("Z17")
     ("Z16")
     ("Z15")
     ("Z14")
     ("Z13")
     ("Z12")
     ("Z11")
     ("Z10")
     ("Z9")
     ("Z8")
     ("Z7")
     ("Z6")
     ("Z5")
     ("Z4")
     ("Z3")
     ("Z2")
     ("Z1")
     ("Z0")
     ("Z01")
     ("ZA18")
     ("ZA17")
     ("ZA16")
     ("ZA15")
     ("ZA14")
     ("ZA13")
     ("ZA12")
     ("ZA11")
     ("ZA10")
     ("ZA9")
     ("ZA8")
     ("ZA7")
     ("ZA6")
     ("ZA5")
     ("ZA4")
     ("ZA3")
     ("ZA2")
     ("ZA1")
     ("ZA0")
     ("ZA01")
     ("ZB18")
     ("ZB17")
     ("ZB16")
     ("ZB15")
     ("ZB14")
     ("ZB13")
     ("ZB12")
     ("ZB11")
     ("ZB10")
     ("ZB9")
     ("ZB8")
     ("ZB7")
     ("ZB6")
     ("ZB5")
     ("ZB4")
     ("ZB3")
     ("ZB2")
     ("ZB1")
     ("ZB0")
     ("ZB01")
     ("ZC18")
     ("ZC17")
     ("ZC16")
     ("ZC15")
     ("ZC14")
     ("ZC13")
     ("ZC12")
     ("ZC11")
     ("ZC10")
     ("ZC9")
     ("ZC8")
     ("ZC7")
     ("ZC6")
     ("ZC5")
     ("ZC4")
     ("ZC3")
     ("ZC2")
     ("ZC1")
     ("ZC0")
     ("ZC01")
    )
)

(mapcar
  (function
    (lambda (el / val_len dop_name dop_up dop_low interval)
      (setq
	val_len	 (car el)
	dop_name (cadr el)
	dop_up	 (caddr el)
	dop_low	 (cadddr el)
	interval (cdr(assoc val_len lst_dist_interval))
	old_elem (assoc dop_name kvalitet_name_lst)
	old_elem_lst (cadr old_elem)
	new_elem_lst (cons (append interval(list dop_up dop_low))old_elem_lst)
      )
      (setq
	kvalitet_name_lst
	 (subst  (list dop_name new_elem_lst ) old_elem  kvalitet_name_lst)
      )
      t
    )
  )
  dp_data
)
