(vl-load-com)

;;;f;;; ("v3d->list" "Выполняет преобразование vla3d точки в список её координат.")

(defun v3d->list (v3d) (vlax-safearray->list (vlax-variant-value v3d)))

;;;f;;; ("is-collinear"
;;;f;;; "Выполняет проверку двух отрезков на коллинеарность.
;;;f;;; Возвращает:
;;;f;;; T - отрезки коллинеарны;
;;;f;;; nil - отрезки не коллинеарны.
;;;f;;; Параметры:
;;;f;;; v_line_1 - Vla объект, представляющй первый отрезок;
;;;f;;; v_line_2 - Vla объект, представляющй второй отрезок;
;;;f;;; delta - точность, расстояние от точки до отрезка при котором объекты считаются коллинеарными.
;;;f;;; Пример использования:
;;;f;;; (vl-load-com)
;;;f;;; (entmake '((0 . \"LINE\") (10 0.0 0.0 0.0) (11 10.0 10.0 0.0)))
;;;f;;; (setq vl1 (vlax-ename->vla-object(entlast)))
;;;f;;; (entmake '((0 . \"LINE\") (10 20.0 20.0 0.0) (11 30.0 30.0 0.0)))
;;;f;;; (setq vl2 (vlax-ename->vla-object(entlast)))
;;;f;;; (entmake '((0 . \"LINE\") (10 25.0 20.0 0.0) (11 35.0 30.0 0.0)))
;;;f;;; (setq vl3 (vlax-ename->vla-object(entlast)))
;;;f;;; (is-collinear vl1 vl2 0.0001)
;;;f;;; (is-collinear vl1 vl3 0.0001)
;;;f;;; ")

(defun is-collinear  (v_line_1          ; Vla объект, представляющй первый отрезок
                      v_line_2          ; Vla объект, представляющй второй отрезок
                      delta             ; Точность, расстояние при котором объекты считаются коллинеарными
                      / v_tmp)
  (if (< (vlax-get-property v_line_1 'length) (vlax-get-property v_line_2 'length))
    (setq v_tmp    v_line_1
          v_line_1 v_line_2
          v_line_2 v_tmp))
  (setq sp (v3d->list (vlax-get-property v_line_2 'startpoint))
        ep (v3d->list (vlax-get-property v_line_2 'endpoint)))
  (and (< (distance sp (vlax-curve-getclosestpointto v_line_1 sp t)) delta)
       (< (distance ep (vlax-curve-getclosestpointto v_line_1 ep t)) delta)))


(defun is-pnt-on-line  (pnt v_line delta)
  (< (distance pnt (vlax-curve-getclosestpointto v_line pnt nil)) delta))

(defun dist-from-pnt-to-curve  (pnt v_curve ext)
  (distance pnt (vlax-curve-getclosestpointto vname pnt ext)))

;;;f;;; (
;;;f;;; "concatenate_two_lines"
;;;f;;; "
;;;f;;; Выполняет объединение двух отрезков.
;;;f;;; Возвращает список из удаляемых отрезков.
;;;f;;; Параметры.
;;;f;;; v_line_1 - Vla объект, предвтавляющий первый отрезок
;;;f;;; v_line_2 - Vla объект, предвтавляющий второй отрезок
;;;f;;; delta - Точность, максимальное расстояние между точкой и отрезком при котором они считаются совпадающими
;;;f;;; filter
;;;f;;; "
;;;f;;; )

(defun concatenate_two_lines  (v_line_1 ; Vla объект, предвтавляющий первый отрезок
                               v_line_2 ; Vla объект, предвтавляющий второй отрезок
                               delta    ; Точность, максимальное расстояние между точкой и отрезком при котором они считаются совпадающими
                               filter / ;
                               lns_clnr ; признак коллинеарности отрезков
                               vl1s     ; Список координат начальной точки первого отрезка
                               vl1e     ; Список координат конечной точки первого отрезка
                               vl2s     ; Список координат начальной точки второго отрезка
                               vl2e     ; Список координат конечной точки второго отрезка
                               vl1e_on_vl2 ; Конечная точка первого отрезка лежит на втором отрезке
                               vl1s_on_vl2 ; Начальная точка первого отрезка лежит на втором отрезке
                               vl2e_on_vl1 ; Конечная точка второго отрезка лежит на первом отрезке
                               vl2s_on_vl1 ; Начальная точка второго отрезка лежит на первом отрезке
                               fltrd    ;
) (setq lns_clnr    (is-collinear v_line_1 v_line_2 delta)
        vl1s        (v3d->list (vlax-get-property v_line_1 'startpoint))
        vl1e        (v3d->list (vlax-get-property v_line_1 'endpoint))
        vl2s        (v3d->list (vlax-get-property v_line_2 'startpoint))
        vl2e        (v3d->list (vlax-get-property v_line_2 'endpoint))
        vl2s_on_vl1 (is-pnt-on-line vl2s v_line_1 delta)
        vl2e_on_vl1 (is-pnt-on-line vl2e v_line_1 delta)
        vl1s_on_vl2 (is-pnt-on-line vl1s v_line_2 delta)
        vl1e_on_vl2 (is-pnt-on-line vl1e v_line_2 delta)
        fltrd       (not (is-prop-lst-same v_line_1 v_line_2 filter)))
  (cond ;;Нет коллинеарности отрезков
        ((not lns_clnr) nil)
        ;; Фильтр по свойствам отрезков
        (fltrd nil)
        ;; Первый отрезок полностью лежит на втором отрезке
        ((and vl1s_on_vl2 vl1e_on_vl2) (vlax-invoke-method v_line_1 'delete) (list v_line_1))
        ;; Второй отрезок полностью лежит на первом отрезке
        ((and vl2s_on_vl1 vl2e_on_vl1) (vlax-invoke-method v_line_2 'delete) (list v_line_2))
        ;; Конечная точка второго отрезка лежит на первом отрезке
        ;; и
        ;; Конечная точка первого отрезка лежит на втором отрезке
        ((and (null vl2s_on_vl1) vl2e_on_vl1 (null vl1s_on_vl2) vl1e_on_vl2)
         (if (> (vlax-get-property v_line_1 'length) (vlax-get-property v_line_2 'length))
           (progn (vlax-put-property v_line_1 'endpoint (vlax-get-property v_line_2 'startpoint))
                  (vlax-invoke-method v_line_2 'delete)
                  (list v_line_2))
           (progn (vlax-put-property v_line_2 'endpoint (vlax-get-property v_line_1 'startpoint))
                  (vlax-invoke-method v_line_1 'delete)
                  (list v_line_1))))
        ;; Конечная точка второго отрезка лежит на первом отрезке
        ;; и
        ;; Начальная точка первого отрезка лежит на втором отрезке
        ((and (null vl2s_on_vl1) vl2e_on_vl1 vl1s_on_vl2 (null vl1e_on_vl2))
         (if (> (vlax-get-property v_line_1 'length) (vlax-get-property v_line_2 'length))
           (progn (vlax-put-property v_line_1 'startpoint (vlax-get-property v_line_2 'startpoint))
                  (vlax-invoke-method v_line_2 'delete)
                  (list v_line_2))
           (progn (vlax-put-property v_line_2 'endpoint (vlax-get-property v_line_1 'endpoint))
                  (vlax-invoke-method v_line_1 'delete)
                  (list v_line_1))))
        ;; Начальная точка второго отрезка лежит на первом отрезке
        ;; и
        ;; Конечная точка первого отрезка лежит на втором отрезке
        ((and vl2s_on_vl1 (null vl2e_on_vl1) (null vl1s_on_vl2) vl1e_on_vl2)
         (if (> (vlax-get-property v_line_1 'length) (vlax-get-property v_line_2 'length))
           (progn (vlax-put-property v_line_1 'endpoint (vlax-get-property v_line_2 'endpoint))
                  (vlax-invoke-method v_line_2 'delete)
                  (list v_line_2))
           (progn (vlax-put-property v_line_2 'startpoint (vlax-get-property v_line_1 'startpoint))
                  (vlax-invoke-method v_line_1 'delete)
                  (list v_line_1))))
        ;;Начальная точка второго отрезка лежит на первом отрезке
        ;; и
        ;;Начальная точка первого отрезка лежит на втором отрезке
        ((and vl2s_on_vl1 (null vl2e_on_vl1) vl1s_on_vl2 (null vl1e_on_vl2))
         (if (> (vlax-get-property v_line_1 'length) (vlax-get-property v_line_2 'length))
           (progn (vlax-put-property v_line_1 'startpoint (vlax-get-property v_line_2 'endpoint))
                  (vlax-invoke-method v_line_2 'delete)
                  (list v_line_2))
           (progn (vlax-put-property v_line_2 'startpoint (vlax-get-property v_line_1 'endpoint))
                  (vlax-invoke-method v_line_1 'delete)
                  (list v_line_1))))
        ;; Отрезки коллинеарны, но общих точек нет
        ((and (null vl2s_on_vl1) (null vl2e_on_vl1) (null vl1s_on_vl2) (null vl1e_on_vl2)) nil)
        ;; Не пойми что
        (t (princ "\nСлучай не обрабатывается\n") nil)))

;;; (is-prop-same(vlax-ename->vla-object (car (entsel ))) (vlax-ename->vla-object (car (entsel ))) 'LineType)
;;; (is-prop-same(vlax-ename->vla-object (car (entsel ))) (vlax-ename->vla-object (car (entsel ))) 'TrueColor)
(defun is-prop-same  (vl1               ; Первый vla-объект
                      vl2               ; Первый vla-объект
                      pr                ; Имя сравниваемого свойства
                      /                 ;
                      vc1               ; vla-Цвет первого объекта
                      vc2               ; vla-Цвет второго объекта
) (cond ((or (= pr 'layer) (= pr 'linetype)) (eq (vlax-get-property vl1 pr) (vlax-get-property vl2 pr)))
        ((= pr 'truecolor)
         (setq vc1 (vlax-get-property vl1 'truecolor)
               vc2 (vlax-get-property vl2 'truecolor))
         (and (= (vlax-get-property vc1 'red) (vlax-get-property vc2 'red))
              (= (vlax-get-property vc1 'green) (vlax-get-property vc2 'green))
              (= (vlax-get-property vc1 'blue) (vlax-get-property vc2 'blue))))
        (t)))

;;;(is-prop-lst-same(vlax-ename->vla-object (car (entsel ))) (vlax-ename->vla-object (car (entsel ))) (list 'TrueColor 'Layer 'LineType))
(defun is-prop-lst-same  (vl1           ; Первый vla-объект
                          vl2           ; Первый vla-объект
                          pr_lst        ; Список тмен сравниваемых свойств
                          )
  (apply (function and) (mapcar (function (lambda (el) (is-prop-same vl1 vl2 el))) pr_lst)))

;;; Конкатенация коллинеарных отрезков заданных в списке vla_lst
;;; delta - расстояние от точки одного отрезка до другого отрезка при котором считается, что точка лежит на отрезке.
(defun concat_lst  (vla_lst             ; Список элементов для объединения
                    delta               ; Точность
                    /                   ;
                    rmd_lst             ; Список, содержащий удаленные объекты
                    vla_tmp_lst do      ; признак продолжения выполнения цикла
                    i j)
  (setq do t)
  (while do
    (setq i (length vla_lst))
    (while (<= 0 (setq i (1- i)))
      (setq j i)
      (while (<= 0 (setq j (1- j)))
        (setq vli (nth i vla_lst)
              vlj (nth j vla_lst))
        (if (and (not (member vli rmd_lst)) (not (member vlj rmd_lst)))
          (progn (mapcar (function (lambda (el)
                                     (if (not (member el rmd_lst))
                                       (setq rmd_lst (cons el rmd_lst)))))
                         (concatenate_two_lines vli vlj delta filter))))))
    (mapcar (function (lambda (el)
                        (if (not (member el rmd_lst))
                          (setq vla_tmp_lst (cons el vla_tmp_lst)))))
            vla_lst)
    (if rmd_lst
      (setq do t)
      (setq do nil))
    (setq rmd_lst nil
          vla_lst vla_tmp_lst)))


;;;;;;("j_lns"
;;;;;;  "Выполняет объединение отрезков, замещая смежные и совпадающие части нескольких отрезков одним отрезком."
;;;;;;  "Измени"
;;;;;;)

(defun c:j_lns  (/                      ;
                 ss                     ; Набор выбора
                 i                      ; Переменная цикла
                 vla_lst                ; Список, содержащий vla - имена элементов
                 c_lst                  ; Промежуточный список, в который попадают коллинеарные элементы
                 r_lst                  ; Промежуточный список в который  попадают не коллинеарные элементы
                 rez_lst                ;
                 filter delta)
  (err-init '("cmdecho"))
  (setq ss     (ssget '((0 . "LINE")))
        i      (sslength ss)
        delta  0.000001
        filter (line-concat-dlg))
  (while (<= 0 (setq i (1- i))) (setq vla_lst (cons (vlax-ename->vla-object (ssname ss i)) vla_lst)))
  (while vla_lst
    (setq c_lst   (cons (car vla_lst) c_lst)
          vla_lst (cdr vla_lst))
    (mapcar (function (lambda (el)
                        (if (is-collinear (car c_lst) el delta)
                          (setq c_lst (cons el c_lst))
                          (setq r_lst (cons el r_lst)))))
            vla_lst)
    (if (< 1 (length c_lst))
      (setq rez_lst (cons c_lst rez_lst)))
    (setq vla_lst r_lst
          c_lst   nil
          r_lst   nil))
  (mapcar (function (lambda (el)
                      (setq el
                             (vl-sort el
                                      (function (lambda (e1 e2) (> (vlax-get-property e1 'length) (vlax-get-property e2 'length))))))
                      (concat_lst el delta)))
          rez_lst)
  (err-handle ""))


(defun line-concat-dlg  (/ dcl_id       ; id диалога
                         setup_lst      ; список с параметрами диалога
                         line-concat-dlg_pos ; Положение диалога на экране
                         do_dialog      ; признак продолжения выполнения диалога
                         rez            ; возвращаемый фильтр
) (setq setup_lst (list '("tgl_Layer" "0") '("tgl_TrueColor" "0") '("tgl_LineType" "0"))
        line-concat-dlg_pos
         '(-1 -1)
        do_dialog t)
  (setq dcl_id (load_dialog "./src/lsp/lines/line_concat.dcl"))
  (while do_dialog
    (if (not (new_dialog "line_concat" dcl_id "" dia_weld_pos))
      (exit))
    (init_dlg setup_lst)
    (action-tile_dlg "setup_lst" "setup_lst" "" "")
    (action_tile "help" "(lines-j_lns-help)")
    (action_tile "info" "(lines-j_lns-info)")
    (setq action (start_dialog))
    (cond ((= action 1) (setq rez (ac_accept_do)) (setq do_dialog nil))
          ((= action 0) (ac_cancel_do) (setq do_dialog nil))
          (setq do_dialog nil)))
  (unload_dialog dcl_id)
  rez)

(defun ac_accept_do  (/ rez_lst)
  (if (= "1" (cadr (assoc "tgl_Layer" setup_lst)))
    (setq rez_lst (cons 'layer rez_lst)))
  (if (= "1" (cadr (assoc "tgl_TrueColor" setup_lst)))
    (setq rez_lst (cons 'truecolor rez_lst)))
  (if (= "1" (cadr (assoc "tgl_LineType" setup_lst)))
    (setq rez_lst (cons 'linetype rez_lst)))
  rez_lst)

(defun ac_cancel_do () nil)

(defun lines-j_lns-info () (alert (strcat "Объединение наложенных друг на друга отрезков " (about-gpl-string))))

(defun lines-j_lns-help() (help (strcat (acad_help) "/j_lns/j_lns.html")))


;;;(defun c:cccc()
;;;  (concatenate_two_lines
;;;    (vlax-ename->vla-object (car (entsel)))
;;;    (vlax-ename->vla-object (car (entsel)))
;;;    0.0001
;;;    nil
;;;  )
;;;)
