(setq spring-setup_msg
       '(("d" "Диаметр проволоки, мм")
         ("D1" "Диаметр пружины наружный, мм")
         ("D" "Диаметр пружины средний, мм")
         ("L0" "Высота пружины в свободном состоянии, мм")
         ("L1" "Высота пружины при предварительной деформации, мм")
         ("L2" "Высота пружины при рабочей деформации, мм")
         ("L3" "Высота пружины при максимальной деформации, мм")
         ("L4" "Высота пружины при соприкосновении витков, мм")
         ("S1" "Предварительная деформация пружины, мм")
         ("S2" "Рабочая деформация пружины, мм")
         ("S3" "Максимальная деформация пружины, мм")
         ("t" "Шаг пружины в свободном состоянии, мм")
         ("Sk" "Толщина конца опорного витка пружины, мм")
         ("h" "Рабочий ход пружины, мм")
         ("L" "Длина проволоки развернутой пружины, мм")
         ("n" "Число витков пружины")
         ("n1" "Полное число витков пружины")
         ("i" "Индекс пружины")
         ("K1" "Коэффициент, учитывающий влияние кривизны витка")
         ("K2" "Коэффициент, учитывающий влияние поперечной силы")
         ("F1" "Сила пружины при предварительной деформации, Н")
         ("F2" "Сила пружины при рабочей деформации, Н")
         ("F3" "Сила пружины при максимальной деформации, Н")
         ("tau1" "Напряжение при кручении при предварительной деформации, МПа")
         ("tau2" "Напряжение при кручении при рабочей деформации, МПа")
         ("tau3" "Напряжение при кручении при максимальной деформации, МПа")
         ("[tau]" "Допускаемое напряжение при кручении, МПа")
         ("C" "Жесткость пружины, Н/мм")
         ("G" "Модуль сдвига, МПа")
         ("i1" "Отношение длины пружины в свободном состоянии к её среднему диаметру")
         ("m" "Масса пружины, кг")))

(defun c:spring  (/ action dcl_id do_dialog)
  (setq setup_lst '(("d" "1.0")           ; Диаметр проволоки, мм
                  ("D1" "24.0")         ; Диаметр пружины наружный, мм
                  ("D" "23.0")          ; Диаметр пружины средний, мм
                  ("L0" "32")           ; Высота пружины в свободном состоянии, мм
                  ("L1" "30.0")         ; Высота пружины при предварительной деформации, мм
                  ("L2" "25.0")         ; Высота пружины при рабочей деформации, мм
                  ("L3" "22.0")         ; Высота пружины при максимальной деформации, мм
                  ("L4" "5.5")          ; Высота пружины при соприкосновении витков, мм
                  ("S1" "30.0")         ; Предварительная деформация пружины, мм
                  ("S2" "25.0")         ; Рабочая деформация пружины, мм
                  ("S3" "22.0")         ; Максимальная деформация пружины, мм
                  ("t" "8.125")         ; Шаг пружины в свободном состоянии, мм
                  ("Sk" "0.5")          ; Толщина конца опорного витка пружины, мм
                  ("h" "10.0")          ; Рабочий ход пружины, мм
                  ("L" "200.0")         ; Длина проволоки развернутой пружины, мм
                  ("n" "4.0")           ; Число витков пружины
                  ("n1" "6.0")          ; Полное число витков пружины
                  ("i" "")              ; Индекс пружины
                  ("K1" "")             ; Коэффициент, учитывающий влияние кривизны витка
                  ("K2" "")             ; Коэффициент, учитывающий влияние поперечной силы
                  ("F1" "")             ; Сила пружины при предварительной деформации, Н
                  ("F2" "")             ; Сила пружины при рабочей деформации, Н
                  ("F3" "")             ; Сила пружины при максимальной деформации, Н
                  ("tau1" "")           ; Напряжение при кручении при предварительной деформации, МПа
                  ("tau2" "")           ; Напряжение при кручении при рабочей деформации, МПа
                  ("tau3" "")           ; Напряжение при кручении при максимальной деформации, МПа
                  ("[tau]" "640.0")     ; Допускаемое напряжение при кручении
                  ("C" "")              ; Жесткость пружины, Н/мм
                  ("G" "72600.0")       ; Модуль сдвига, МПа
                  ("i1" "")             ; Отношение длины пружины в свободном состоянии к её среднему диаметру
                  ("m" "")              ; Масса пружины, кг
                  ))
  (setq dcl_id (load_dialog "./src/lsp/prj/spring/Spring.DCL"))
  ;;  ;; "E:/home/namatv/git/GitHub/mnasoft/MNAS_acad_utils/src/lsp/prj/spring/Spring.DCL"
  (setq do_dialog t)
  (while do_dialog
    (if (not (new_dialog "spring" dcl_id))
      (exit))
    (init_dlg setup_lst)
    (action-tile_dlg "setup_lst" "setup_lst" "(spring-err)" "")
    (action_tile "d" "(spring-action_d)")
    (action_tile "D" "(spring-actionD)")
    (action_tile "D1" "(spring-actionD1)")
    (action_tile "n1" "(spring-action_n1)")
    (action_tile "n" "(spring-action_n)")
    (action_tile "t" "(spring-action_t)")
    (action_tile "L0" "(spring-actionL0)")
    (action_tile "S1" "(spring-actionS1)")
    (action_tile "L1" "(spring-actionL1)")
    (action_tile "S2" "(spring-actionS2)")
    (action_tile "L2" "(spring-actionL2)")
    (action_tile "S3" "(spring-actionS3)")
    (action_tile "L3" "(spring-actionL3)")
    (action_tile "G" "(spring-actionG)")
    (action_tile "info" "(spring-info)")
    (action_tile "help" "(spring-help)")
    (action_tile "Print" "(spring-print-html)")
    (action_tile "Draw" "(done_dialog 2)")
    (setq action (start_dialog))
    (cond ((= action 0) (setq do_dialog nil))
          ((= action 1) (setq do_dialog nil))
          ((= action 2) (spring-draw))))
  (unload_dialog dcl_id)
;;;  (setq *error* old_err)
;;;  (command-s "_.undo" "_end")
;;;  (setvar "cmdecho" 1)
  )

;;Функция для сохранения списка параметров в переменной setup_lst.
(defun spring-save-setup-lst () (setq setup_lst (action-save_dlg setup_lst)))

(defun spring-info () (alert (strcat "Расчет пружины сжатия " (about-gpl-string))))

(defun spring-help () (help (strcat (acad_help) "/spring/spring.html")))
