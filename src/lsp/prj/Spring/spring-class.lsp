(defun spring-get (key) (setq tmp (atof (get_tile key))) (set_tile key (rtos tmp)) tmp)

(defun spring-put (key val) (atof (set_tile key (rtos val))))

(defun spring-d () (spring-put "D" (- (spring-get "D1") (spring-get "d"))))

(defun spring-d1 () (spring-put "D1" (+ (spring-get "d") (spring-get "D"))))

(defun spring-_i () (spring-put "i" (/ (spring-get "D") (spring-get "d"))))

(defun spring-_i1 () (spring-put "i1" (/ (spring-get "L0") (spring-get "D"))))

(defun spring-l0  ()
  (spring-put "L0" (+ (* (spring-get "n") (spring-get "t")) (* 1.5 (spring-get "d")))))

(defun spring-l1 () (spring-put "L1" (- (spring-get "L0") (spring-get "S1"))))

(defun spring-l2 () (spring-put "L2" (- (spring-get "L0") (spring-get "S2"))))

(defun spring-l3 () (spring-put "L3" (- (spring-get "L0") (spring-get "S3"))))

(defun spring-l4 () (spring-put "L4" (* (+ (spring-get "n") 1.5) (spring-get "d"))))

(defun spring-s1 () (spring-put "S1" (- (spring-get "L0") (spring-get "L1"))))

(defun spring-s2 () (spring-put "S2" (- (spring-get "L0") (spring-get "L2"))))

(defun spring-s3 () (spring-put "S3" (- (spring-get "L0") (spring-get "L3"))))

(defun spring-l  (/ d _t)
  (setq d  (spring-get "D")
        _t (spring-get "t"))
  (spring-put "L" (* (spring-get "n1") (sqrt (+ (* pi pi d d) (* _t _t))))))

(defun spring-_n () (spring-put "n" (- (spring-get "n1") 2.0)))

(defun spring-_n1 () (spring-put "n1" (+ (spring-get "n") 2.0)))

(defun spring-_t  ()
  (spring-put "t" (/ (- (spring-get "L0") (* 1.5 (spring-get "d"))) (spring-get "n"))))

(defun spring-_h () (spring-put "h" (- (spring-get "S2") (spring-get "S1"))))

(defun spring-k1  (/ i)
  (setq i (spring-_i))
  (spring-put "K1" (+ (/ (- (* 4.0 i) 1.0) (- (* 4.0 i) 4.0)) (/ 0.615 i))))

(defun spring-k2  (/ i)
  (setq i (spring-_i))
  (spring-put "K2" (+ 1.0 (/ 1.0 2.0 i) (/ -1.0 2.0 i i))))

(defun spring-f1  (/ d_big d_sm)
  (setq d_sm  (spring-get "d")
        d_big (spring-get "D"))
  (spring-put "F1"
              (/ (* (spring-get "G") d_sm d_sm d_sm d_sm (spring-get "S1"))
                 8.0
                 d_big
                 d_big
                 d_big
                 (spring-get "n")
                 (spring-k2))))

(defun spring-f2  (/ d_big d_sm)
  (setq d_sm  (spring-get "d")
        d_big (spring-get "D"))
  (spring-put "F2"
              (/ (* (spring-get "G") d_sm d_sm d_sm d_sm (spring-get "S2"))
                 8.0
                 d_big
                 d_big
                 d_big
                 (spring-get "n")
                 (spring-k2))))

(defun spring-f3  (/ d_big d_sm)
  (setq d_sm  (spring-get "d")
        d_big (spring-get "D"))
  (spring-put "F3"
              (/ (* (spring-get "G") d_sm d_sm d_sm d_sm (spring-get "S3"))
                 8.0
                 d_big
                 d_big
                 d_big
                 (spring-get "n")
                 (spring-k2))))

(defun spring-_tau1  ()
  (setq d_sm (spring-get "d"))
  (spring-put "tau1"
              (/ (* 2.55 (spring-get "F1") (spring-get "D") (spring-get "K1")) (* d_sm d_sm d_sm))))

(defun spring-_tau2  ()
  (setq d_sm (spring-get "d"))
  (spring-put "tau2"
              (/ (* 2.55 (spring-get "F2") (spring-get "D") (spring-get "K1")) (* d_sm d_sm d_sm))))
(defun spring-_tau3  ()
  (setq d_sm (spring-get "d"))
  (spring-put "tau3"
              (/ (* 2.55 (spring-get "F3") (spring-get "D") (spring-get "K1")) (* d_sm d_sm d_sm))))

(defun spring-c () (spring-put "C" (/ (- (spring-get "F2") (spring-get "F1")) (spring-get "h"))))

(defun spring-m  (/ _d _n1)
  (setq _d  (spring-get "d")
        _n1 (spring-get "n1"))
  (spring-put "m" (* 8.0e-6 pi _d _d 0.25 (spring-get "L") (/ (- _n1 0.5) _n1))))

(defun spring-err () (set_tile "error" (strcat (cadr (assoc $key spring-setup_msg)) " = " $value)))


(defun spring-action_d  ()
  (spring-err)
  (spring-_t)
  (spring-l4)
  (spring-d1)
  (spring-d)
  (spring-_i1)
  (spring-l)
  (spring-_i)
  (spring-k2)
  (spring-f1)
  (spring-f2)
  (spring-f3)
  (spring-k1)
  (spring-_tau1)
  (spring-_tau2)
  (spring-_tau3)
  (spring-c)
  (spring-m)
  (spring-save-setup-lst))

(defun spring-actiond  ()
  (spring-err)
  (spring-d1)
  (spring-_i1)
  (spring-l)
  (spring-_i)
  (spring-k2)
  (spring-f1)
  (spring-f2)
  (spring-f3)
  (spring-k1)
  (spring-_tau1)
  (spring-_tau2)
  (spring-_tau3)
  (spring-c)
  (spring-m)
  (spring-save-setup-lst))

(defun spring-actiond1  ()
  (spring-err)
  (spring-d)
  (spring-_i1)
  (spring-l)
  (spring-_i)
  (spring-k2)
  (spring-f1)
  (spring-f2)
  (spring-f3)
  (spring-k1)
  (spring-_tau1)
  (spring-_tau2)
  (spring-_tau3)
  (spring-c)
  (spring-m)
  (spring-save-setup-lst))

(defun spring-action_n1  ()
  (spring-err)
  (spring-_n)
  (spring-l4)
  (spring-l0)
  (spring-_t)
  (spring-_i1)
  (spring-l)
  (spring-l1)
  (spring-l2)
  (spring-l3)
  (spring-s1)
  (spring-s2)
  (spring-s3)
  (spring-_h)
  (spring-f1)
  (spring-f2)
  (spring-f3)
  (spring-_tau1)
  (spring-_tau2)
  (spring-_tau3)
  (spring-c)
  (spring-m)
  (spring-save-setup-lst))

(defun spring-action_n  ()
  (spring-err)
  (spring-_n1)
  (spring-l4)
  (spring-l0)
  (spring-_t)
  (spring-_i1)
  (spring-l)
  (spring-l1)
  (spring-l2)
  (spring-l3)
  (spring-s1)
  (spring-s2)
  (spring-s3)
  (spring-_h)
  (spring-f1)
  (spring-f2)
  (spring-f3)
  (spring-_tau1)
  (spring-_tau2)
  (spring-_tau3)
  (spring-c)
  (spring-m)
  (spring-save-setup-lst))

(defun spring-action_t  ()
  (spring-err)
  (spring-l)
  (spring-l0)
  (spring-_t)
  (spring-_i1)
  (spring-l)
  (spring-l1)
  (spring-l2)
  (spring-l3)
  (spring-s1)
  (spring-s2)
  (spring-s3)
  (spring-_h)
  (spring-f1)
  (spring-f2)
  (spring-f3)
  (spring-_tau1)
  (spring-_tau2)
  (spring-_tau3)
  (spring-c)
  (spring-m)
  (spring-save-setup-lst))

(defun spring-actionl0  ()
  (spring-err)
  (spring-_t)
  (spring-_i1)
  (spring-l)
  (spring-l1)
  (spring-l2)
  (spring-l3)
  (spring-s1)
  (spring-s2)
  (spring-s3)
  (spring-_h)
  (spring-f1)
  (spring-f2)
  (spring-f3)
  (spring-_tau1)
  (spring-_tau2)
  (spring-_tau3)
  (spring-c)
  (spring-m)
  (spring-save-setup-lst))

(defun spring-actions1  ()
  (spring-err)
  (spring-l1)
  (spring-_h)
  (spring-f1)
  (spring-_tau1)
  (spring-c)
  (spring-m)
  (spring-save-setup-lst))

(defun spring-actionl1  ()
  (spring-err)
  (spring-s1)
  (spring-_h)
  (spring-f1)
  (spring-_tau1)
  (spring-c)
  (spring-m)
  (spring-save-setup-lst))

(defun spring-actions2  ()
  (spring-err)
  (spring-l2)
  (spring-_h)
  (spring-f2)
  (spring-_tau2)
  (spring-c)
  (spring-m)
  (spring-save-setup-lst))

(defun spring-actionl2  ()
  (spring-err)
  (spring-s2)
  (spring-_h)
  (spring-f2)
  (spring-_tau2)
  (spring-c)
  (spring-m)
  (spring-save-setup-lst))

(defun spring-actions3  ()
  (spring-err)
  (spring-l3)
  (spring-f3)
  (spring-_tau3)
  (spring-save-setup-lst))

(defun spring-actionl3  ()
  (spring-err)
  (spring-s3)
  (spring-f3)
  (spring-_tau3)
  (spring-save-setup-lst))

(defun spring-actiong  ()
  (spring-err)
  (spring-f1)
  (spring-f2)
  (spring-f3)
  (spring-_tau1)
  (spring-_tau2)
  (spring-_tau3)
  (spring-c)
  (spring-m)
  (spring-save-setup-lst))
