(setq 001-049 '("001-1"   "001-2"   "001-3"   "001-4"   "001-5"   "001-6"   "001-7"   "001-8"   "001-9"   "001ÑÁ"
                "002-1"   "002-2"   "002-3"   "002-4"   "002ÑÁ-1" "002ÑÁ-2" "003-1"   "003-2"   "003ÑÁ"   "004"
                "004ÑÁ"   "005"     "005ÑÁ"   "006-1"   "006-2"   "006ÑÁ"   "008"     "008ÑÁ"   "009"     "009ÑÁ"
                "010"     "010ÑÁ"   "015"     "016-1"   "016-2"   "017-1"   "017-2"   "018"     "019"     "020"
                "021"     "022"     "023"     "024"     "025"     "026"     "027"     "028"     "029"     "030"
                "031"     "032"     "033"     "034"     "035"     "036"     "037"     "038"     "039"     "040"
                "041"     "042"     "043"     "044"     "045"     "046"     "047"     "048"     "049")
      lt      (vl-string-subst "" ".dwg" (getvar "dwgname")))


(defun del-layout  (l-name l-lst / l-tmp) ;(command-s "open" l-name)
  (mapcar (function (lambda (el)
                      (if (not (= el l-name))
                        (command-s "layout" "delete" el))))
          l-lst))

(del-layout lt 001-049)
