;;;;;;("rezba_out" "not defined" "not defined")
(defun c:rezba_out  (/       a01     d       dist_p0p1       en_arc3
                     en_line1        en_line2        en_line4
                     h       n_vitkov        p       p0      p1
                     pc      pc5     pc6     pdw     pv1     pv1_1
                     pv2     pw3     r)
  (setq p0 (getpoint "введите первую точку на оси резьбы:")
        p1 (getpoint p0 "введите вторую точку на оси резьбы:")
        p  (getdist "введите шаг резьбы:")
        d  (getdist "введите номинальный диаметр резьбы:"))
  (setq dist_p0p1 (distance p0 p1)
        n_vitkov  (1+ (fix (/ dist_p0p1 p)))
        h         (* (sqrt 3.) p 0.5)
        r         (/ h 6.0))
  (setq a01 (angle p0 p1))
  (setq pv1   (polar p0 (+ (/ pi 2.0) a01) (/ d 2.0))
        pv2   (polar pv1 a01 (/ p 8.0))
        pdw   (polar pv1 (- a01 (/ pi 2.0)) (* (/ 7. 8.) h))
        pw3   (inters pv2
                      (polar pv2 (- a01 (/ pi 3.0)) 1.0)
                      pdw
                      (polar pdw a01 1.0)
                      nil)
        pc    (polar pw3 (+ a01 (/ pi 2.0)) (+ r (/ h 6.0)))
        pc5   (polar pc (- a01 (* (/ 5. 6.) pi)) r)
        pc6   (polar pc (- a01 (* (/ 1. 6.) pi)) r)
        pv1_1 (polar pv1 a01 p))
;;;  (dr:point p0 1)
;;;  (dr:point p1 2)
;;;  (dr:point pv1 3)
;;;  (dr:point pv2 3)
;;;  (dr:point pdw 4)
;;;  (dr:point pw3 5)
;;;  (dr:point pc 6)
;;;  (dr:point pc5 7)
;;;  (dr:point pc6 7)
  (dr:line pv1 pv2 255)
  (setq en_line1 (entlast))
  (dr:line pv2 pc5 255)
  (setq en_line2 (entlast))
  (dr:arc pc
          r
          (+ a01 (* pi (/ 7.0 6.0)))
          (- a01 (* pi (/ 1.0 6.0)))
          1)
  (setq en_arc3 (entlast))
  (dr:line pc6 pv1_1 255)
  (setq en_line4 (entlast))
  (dr:line p0 p1 255)
  (command-s "snap" "r" "non" p0 "non" p1)
  (command-s "-array"  en_line1  en_line2  en_arc3   en_line4
             ""        "r"       "1"       n_vitkov  p)
  (command-s "snap" "r" "0.0,0.0" "0.0")
  (command-s "snap" "off"))

;;;;;;("rezba_in" "not defined" "not defined")
(defun c:rezba_in  (/)
  (setq p0 (getpoint "введите первую точку на оси резьбы:")
        p1 (getpoint p0 "введите вторую точку на оси резьбы:")
        p  (getdist "введите шаг резьбы:")
        d  (getdist "введите номинальный диаметр резьбы:"))
  (setq dist_p0p1 (distance p0 p1)
        n_vitkov  (1+ (fix (/ dist_p0p1 p)))
        h         (* (sqrt 3.) p 0.5)
        r         (/ h 6.0))
  (setq a01 (angle p0 p1))
  (setq pw1 (polar p0 (+ a01 (/ pi 2.0)))))
