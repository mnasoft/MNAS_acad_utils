(setq
  mendeleev_tbl
   '(("H" . 0.001)
     ("C" . 0.012)
     ("N" . 0.014)
     ("O" . 0.016)
    )
)

(setq gas
       '(
	 ("Компонент"		    "Формула-строка"
	  "Формула-состав"	    "Qв, МДж/м3"
	  "Qн, МДж/м3"		    "ro_otn, Относит. Плотность"
	  "ro, Плотность, кг/м3"
	 )
	 ("N2"
	  ("Формула-строка" . "N2")
	  ("Формула-состав" ("N" 2))
	  ("Qв" . 0.0)
	  ("Qн" . 0.0)
	  ("ro_otn" . 0.967)
	 )

	 ("O2"
	  ("Формула-строка" . "O2")
	  ("Формула-состав" ("O" 2))
	  ("Qв" . 0.0)
	  ("Qн" . 0.0)
	  ("ro_otn" . 1.105)
	 )

	 ("CO2"
	  ("Формула-строка" . "CO2")
	  ("Формула-состав" ("C" 1) ("O" 2))
	  ("Qв" . 0.0)
	  ("Qн" . 0.0)
	  ("ro_otn" . 1.529)
	 )

	 ("C1"
	  ("Формула-строка" . "CH4")
	  ("Формула-состав" ("C" 1) ("H" 4))
	  ("Qв" . 37.100)
	  ("Qн" . 33.41)
	  ("ro_otn" . 0.5546)

	 )
	 ("C2"
	  ("Формула-строка" . "C2H6")
	  ("Формула-состав" ("C" 2) ("H" 6))
	  ("Qв" . 65.380)
	  ("Qн" . 59.85)
	  ("ro_otn" . 1.0460)

	 )
	 ("C3"
	  ("Формула-строка" . "C3H8")
	  ("Формула-состав" ("C" 3) ("H" 8))
	  ("Qв" . 93.980)
	  ("Qн" . 86.53)
	  ("ro_otn" . 1.5490)

	 )
	 ("iC4"
	  ("Формула-строка" . "iC3H8")
	  ("Формула-состав" ("C" 4) ("H" 10))
	  ("Qв" . 123.250)
	  ("Qн" . 113.81)
	  ("ro_otn" . 2.0680)

	 )
	 ("nC4"
	  ("Формула-строка" . "nC4H8")
	  ("Формула-состав" ("C" 4) ("H" 10))
	  ("Qв" . 123.720)
	  ("Qн" . 114.27)
	  ("ro_otn" . 2.0710)

	 )
	 ("iC5"
	  ("Формула-строка" . "iC5H10")
	  ("Формула-состав" ("C" 5) ("H" 12))
	  ("Qв" . 155.650)
	  ("Qн" . 144.02)
	  ("ro_otn" . 2.6370)

	 )
	 ("nC5"
	  ("Формула-строка" . "nC5H10")
	  ("Формула-состав" ("C" 5) ("H" 12))
	  ("Qв" . 155.650)
	  ("Qн" . 144.02)
	  ("ro_otn" . 2.6370)

	 )
	 ("H2"
	  ("Формула-строка" . "H2")
	  ("Формула-состав" ("H" 2))
	  ("Qв" . 11.870)
	  ("Qн" . 10.05)
	  ("ro_otn" . 0.0695)

	 )
	)
)


(setq
  состав1_об_%
   '(
     ("C1" . 95.5)
     ("C2" . 0.5)
     ("C3" . 0.5)
     ("N2" . 1.25)
     ("CO2" . 0.25)
     ("O2" . 0.5)
    )
)

(setq состав1_об
       '(("C1" . 0.969543)
	 ("C2" . 0.00507614)
	 ("C3" . 0.00507614)
	 ("N2" . 0.0126904)
	 ("CO2" . 0.00253807)
	 ("O2" . 0.00507614)
	)
)

(setq
  состав2_об_%
   '(
     ("C1" . 6.5)
     ("C2" . 3.9)
     ("C3" . 2.1)
     ("iC4" . 0.3)
     ("nC4" . 0.6)
     ("iC5" . 0.3)
     ("nC5" . 0.2)
     ("H2" . 88.1)
    )
)
     ;Пересчет объемных долей смеси заданных в % в объемные доли смеси
(defun об_%->об_доли (об%)
  (mapcar
    (function
      (lambda (el)
	(cons (car el) (* 0.01 (cdr el)))
      )
    )
    об%
  )
)
     ;Пересчет объемных долей смеси в объемные доли смеси в %
(defun об_доли->об_% (об_доли)
  (mapcar
    (function
      (lambda (el)
	(cons (car el) (* 100. (cdr el)))
      )
    )
    об_доли
  )
)
     ;Пересчет объемных долей смеси в случае некорректной их задачи (сумма объемных долей > или < 1.0)
(defun подгон_об_доли_смеси_1 (состав_об)
  (setq	summa
	 (apply (function +) (mapcar (function cdr) состав_об))
  )
  (mapcar (function (lambda (a) (cons (car a) (/ (cdr a) summa))))
	  состав_об
  )
)
     ;Расчет молярной массы смеси
(defun mu_см[ri] (состав_об)
  (setq
    компоненты	  (mapcar 'car состав_об)
    объемные_доли (mapcar 'cdr состав_об)
    формулы
		  (mapcar
		    (function
		      (lambda (el)
			(cdr (assoc "Формула-состав" (cdr (assoc el gas))))
		      )
		    )
		    компоненты
		  )
  )
  (setq	мол_массы
		  (mapcar
		    (function
		      (lambda (el)
			(mapcar
			  (function
			    (lambda (ddd)
			      (* (cdr (assoc (car ddd) mendeleev_tbl)) (cadr ddd))
			    )
			  )
			  el
			)
		      )
		    )
		    формулы
		  )
	мол_массы (mapcar
		    (function
		      (lambda (el)
			(apply (function +) el)
		      )
		    )
		    мол_массы
		  )
  )
  (apply '+ (mapcar '* мол_массы объемные_доли))
)
     ;Расчет плотности смеси
(defun ро_cm (mu_cm P_cm T_cm)
  (/ (* mu_cm P_cm) (* 8.314 T_cm))
)

;Расчет низшей теплоты сгорания смеси
(defun Q_рн ()
  (setq
    Q (mapcar
	(function
	  (lambda (el)
	    (cdr (assoc "Qн" (cdr (assoc el gas))))
	  )
	)
	компоненты
      )
  )
  (apply '+ (mapcar '* Q объемные_доли))
)
 ;Расчет высшей теплоты сгорания смеси
(defun Q_рв ()
  (setq
    Q (mapcar
	(function
	  (lambda (el)
	    (cdr (assoc "Qв" (cdr (assoc el gas))))
	  )
	)
	компоненты
      )
  )
  (apply '+ (mapcar '* Q объемные_доли))
)
;Определение плотности составляющих смесь комплексных газов
(ро_cm (mu_см[ri]
	 (подгон_об_доли_смеси_1 (об_%->об_доли состав1_об_%))
       )
       (getreal "Введите Р:  ")
       (getreal "Введите T:  ")
)
(ро_cm (mu_см[ri]
	 (подгон_об_доли_смеси_1 (об_%->об_доли состав2_об_%))
       )
       (getreal "Введите Р:  ")
       (getreal "Введите T:  ")
)
;Определение плотности смеси комплексных газов
(setq mu_cm (list (mu_см[ri]
	       (подгон_об_доли_смеси_1 (об_%->об_доли состав1_об_%))
	      )
	      (mu_см[ri]
	       (подгон_об_доли_смеси_1 (об_%->об_доли состав2_об_%))
	      )
	     )
)
(setq P_cm (getreal "Введите Р:  ")
      T_cm (getreal "Введите T:  ")
)
(setq l 0)
(while (<= l 1)
  (setq	об_доли	(list l (- 1 l))
  )
  (print (fix (* l 100)))
  (princ " ")
  (princ
    (ро_cm (apply (function +) (mapcar (function *) об_доли mu_cm))
	   P_cm
	   T_cm
    )
  )
  (setq l (+ l 0.01))
)
 ;|«Visual LISP© Format Options»
(72 2 5 2 nil "end of" 60 15 0 0 0 T T nil T)
;*** DO NOT add text below the comment! ***|;
