;;;;;;("point_block" "Преобразование точки в блок." "Измени")
(defun c:point_block  (/ ed en layer p_10 p_210 ss ss_len x_sc y_sc z_sc a_ro l_type color ED_INS EN_INS NAME_INS SS_INS)
  (princ "\nСсылочный блок:")
  (setq ss_ins   (ssget '((0 . "INSERT")))
        en_ins   (ssname ss_ins 0)
        ed_ins   (entget en_ins)
        name_ins (cdr (assoc 2 ed_ins))
        x_sc     (cdr (assoc 41 ed_ins))
        y_sc     (cdr (assoc 42 ed_ins))
        z_sc     (cdr (assoc 43 ed_ins))
        a_ro     (cdr (assoc 50 ed_ins)))
  (princ "\nТочки для преобразования в блоки:")
  (setq ss (ssget '((0 . "point"))))
  (setq ss_len (sslength ss))
  (while (>= (setq ss_len (1- ss_len)) 0)
    (setq en     (ssname ss ss_len)
          ed     (entget en)
          layer  (cdr (assoc 8 ed))
          p_10   (cdr (assoc 10 ed))
          p_210  (cdr (assoc 210 ed))
          l_type (cdr (assoc 6 ed))
          color  (cdr (assoc 62 ed)))
    (entdel en)
    (entmake (list (cons 0 "INSERT")
                   (cons 2 name_ins)
                   (cons 8 layer)
                   (cons 10 p_10)
                   (cons 41 x_sc)
                   (cons 42 y_sc)
                   (cons 43 z_sc)
                   (cons 50 a_ro)
                   (cons 210 p_210))))
  (princ))


;;;;;;("block_point" "Преобразование блока в точку." "Измени")
(defun c:block_point  (/ ed layer en p_10 p_210 ss ss_len x_sc y_sc z_sc a_ro l_type color)
  (princ "\nБлоки для преобразования их в точки:")
  (setq ss (ssget '((0 . "INSERT"))))
  (setq ss_len (sslength ss))
  (while (>= (setq ss_len (1- ss_len)) 0)
    (setq en     (ssname ss ss_len)
          ed     (entget en)
          layer  (cdr (assoc 8 ed))
          p_10   (cdr (assoc 10 ed))
          p_210  (cdr (assoc 210 ed))
          l_type (cdr (assoc 6 ed))
          color  (cdr (assoc 62 ed)))
    (entdel en)
    (entmake (list (cons 0 "POINT") (cons 8 layer) (cons 10 p_10) (cons 210 p_210))))
  (princ))

;;;;;;("block_block" "Преобразование блока в блок." "Измени")
(defun c:block_block  (/ ED layer EN P_10 p_210 SS SS_LEN x_sc y_sc z_sc a_ro ED_INS EN_INS NAME_INS SS_INS)
  (princ "\nСсылочный блок:")
  (setq ss_ins   (ssget '((0 . "INSERT")))
        en_ins   (ssname ss_ins 0)
        ed_ins   (entget en_ins)
        name_ins (cdr (assoc 2 ed_ins))
        x_sc     (cdr (assoc 41 ed_ins))
        y_sc     (cdr (assoc 42 ed_ins))
        z_sc     (cdr (assoc 43 ed_ins))
        a_ro     (cdr (assoc 50 ed_ins)))
  (princ "\nБлоки для преобразования:")
  (setq ss (ssget '((0 . "INSERT"))))
  (setq ss_len (SSLENGTH ss))
  (while (>= (setq ss_len (1- ss_len)) 0)
    (setq en    (ssname ss ss_len)
          ed    (entget en)
          layer (cdr (assoc 8 ed))
          p_10  (cdr (assoc 10 ed))
          p_210 (cdr (assoc 210 ed)))
    (entdel en)
    (entmake (list (cons 0 "INSERT")
                   (cons 8 "0")
                   (cons 2 name_ins)
                   (cons 8 layer)
                   (cons 10 p_10)
                   (cons 41 x_sc)
                   (cons 42 y_sc)
                   (cons 43 z_sc)
                   (cons 50 a_ro)
                   (cons 210 p_210))))
  (princ))

;;;;;;("block_name" "Преобразование блока в блок." "Измени")
(defun c:block_name  (/ ED layer EN P_10 p_210 SS SS_LEN x_sc y_sc z_sc a_ro)
  (princ "\nСсылочный блок:")
  (setq ss_ins   (ssget '((0 . "INSERT")))
        en_ins   (ssname ss_ins 0)
        ed_ins   (entget en_ins)
        name_ins (cdr (assoc 2 ed_ins)))
  (princ "\nБлоки для преобразования:")
  (setq ss (ssget '((0 . "INSERT"))))
  (setq ss_len (SSLENGTH ss))
  (while (>= (setq ss_len (1- ss_len)) 0)
    (setq en (ssname ss ss_len)
          ed (entget en)
          ed (subst (cons 2 name_ins) (assoc 2 ed) ed))
    (entmod ed))
  (princ))
