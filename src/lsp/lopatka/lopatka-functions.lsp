(defun lo:my_err  (s)
  (if (/= s "Функция прервана")
    (princ (strcat "\nОшибка: " s)))
  (setq *error* olderr)
  (princ))


(defun lo:lop_7  (/ hl lk lp f1 p2_9r1_1 p2_9r2_1 file1)
  (setq file1 (open "lopatka.rez" "a"))
  (if (null file1)
    (progn (alert (strcat "Не могу открыть файл " "lopatka.rez" ".")) (exit)))
  (princ "\n\n Исходные данные: ")
  (princ "\nd1                 = " file1)
  (princ (* r1 2.) file1)
  (princ "\nd2                 = " file1)
  (princ (* r2 2.) file1)
  (princ "\nr1                 = " file1)
  (princ r_1 file1)
  (princ "\nl1                 = " file1)
  (princ l1 file1)
  (princ "\nl2                 = " file1)
  (princ l2 file1)
  (princ "\nh                  = " file1)
  (princ h file1)
  (princ "\na1                 = " file1)
  (princ (* (/ 180. pi) a1) file1)
  (princ "\na2                 = " file1)
  (princ (* (/ 180. pi) a2) file1)
  (princ "\na3                 = " file1)
  (princ (* (/ 180. pi) a3) file1)
  (princ "\n Результаты расчета: " file1)
  (setq p2_9r1_1 (inters p2_9r1 (polar p2_9r1 (+ pi2 (angle p2_7_1 p2_6_3)) h) p2_7_1 p2_6_3 nil))
  (princ "\nРасстояние у корня лопатки        = " file1)
  (princ (setq lk (distance p2_9r1 p2_9r1_1)) file1)
  (princ " ед" file1)
  (setq p2_9r2_1 (inters p2_9r2 (polar p2_9r2 (+ pi2 (angle p2_7_1 p2_6_3)) h) p2_7_1 p2_6_3 nil))
  (princ "\nРасстояние на периферии лопатки   = " file1)
  (princ (setq lp (distance p2_9r2 p2_9r2_1)) file1)
  (princ " ед" file1)
  (princ "\nВысота лопатки                    = " file1)
  (princ (setq hl (distance p1_1 p1_2)) file1)
  (princ " ед" file1)
  (princ "\nКоличество лопаток                = " file1)
  (princ n file1)
  (princ " шт." file1)
  (princ "\nПлощадь одного лопаточного проема = " file1)
  (princ (setq f1 (* (+ lp lk) 0.5 hl)) file1)
  (princ " ед^2" file1)
  (princ "\nПлощадь завихрителя               = " file1)
  (princ (setq f (* f1 n)) file1)
  (princ " ед^2" file1)
  (close file1)
  (princ))
