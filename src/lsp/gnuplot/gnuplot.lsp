(vl-load-com)
    
(defun c:gnuplot-vectors-export  (/ ss en ed vo out)
  (setq out (open (getfiled "Укажите имя файла" "" "data" 1) "w")
        ss  (ssget)
        i   (sslength ss))
  (while (<= 0 (setq i (1- i)))
    (setq en    (ssname ss i)
          ed    (entget en)
          vo    (vlax-ename->vla-object en)
          vo-sp (vlax-curve-getStartParam vo)
          vo-ep (vlax-curve-getEndParam vo))
    (cond ((= (cdr (assoc 0 ed)) "LINE") (gnuplot-export-line-to-vector vo))
          ((= (cdr (assoc 0 ed)) "ARC") (gnuplot-export-arc-to-vector vo))
          ((= (cdr (assoc 0 ed)) "CIRCLE") (gnuplot-export-arc-to-vector vo))))
  (close out))

(defun gnuplot-export-vector  (sp ep)
  (mapcar (function (lambda (el) (princ el out) (princ " " out))) sp)
  (mapcar (function (lambda (el) (princ el out) (princ " " out))) (mapcar (function -) ep sp))
  (princ "\n" out))

(defun gnuplot-export-line-to-vector  (vo / sp ep)
  (setq sp (vlax-curve-getPointAtParam vo (vlax-curve-getStartParam vo))
        ep (vlax-curve-getPointAtParam vo (vlax-curve-getEndParam vo)))
  (gnuplot-export-vector sp ep))

(defun gnuplot-export-arc-to-vector  (vo / s-param e-param sp-delta sp ep sp-i ep-i i n )
  (setq s-param  (vlax-curve-getStartParam vo)
        e-param  (vlax-curve-getEndParam vo)
        n        24
        sp-delta (/ (- e-param s-param) n)
        i        0)
  (while (< i n)
    (setq sp-i (+ s-param (* i sp-delta))
          ep-i (+ s-param (* (1+ i) sp-delta))
          sp   (vlax-curve-getPointAtParam vo sp-i)
          ep   (vlax-curve-getPointAtParam vo ep-i))
    (gnuplot-export-vector sp ep)
    (setq i (1+ i))))

(defun gnuplot-export-circle-to-vector  (vo / s-param e-param sp-delta sp ep sp-i ep-i i n )
  (setq s-param  (vlax-curve-getStartParam vo)
        e-param  (vlax-curve-getEndParam vo)
        n        24
        sp-delta (/ (- e-param s-param) n)
        i        0)
  (while (< i n)
    (setq sp-i (+ s-param (* i sp-delta))
          ep-i (+ s-param (* (1+ i) sp-delta))
          sp   (vlax-curve-getPointAtParam vo sp-i)
          ep   (vlax-curve-getPointAtParam vo ep-i))
    (gnuplot-export-vector sp ep)
    (setq i (1+ i))))
