(setq *for_lic-command-list* '("for_prov" "for_prover" "for_proect" "gr" "pr1" "pr2" "rep"))
;;;; (opech_cmds-str *for_lic-command-list*)

(defun c:ащк_зкщм() (c:for_prov))
(defun c:ащк_зкщмук() (c:for_prover))
(defun c:ащк_зкщусе() (c:for_proect))
(defun c:пк() (c:gr))
(defun c:зк1() (c:pr1))
(defun c:зк2() (c:pr2))
(defun c:куз() (c:rep))

(princ "Loaded project for_lic.\n")
