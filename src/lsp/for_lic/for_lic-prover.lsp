;;;;;;("for_prov"
;;;;;;  "Проверочный расчет жидкотопливной форсунки
;;;;;;Ввод данных выполняется в диалоговом режиме." "Расчеты" )
(defun c:for_prov  (/                   ;
                    old_err             ;
                    fn                  ; Имя файла
                    f1                  ; Дескриптор файла
                    alfa_eps alfa_p   alfa_teta         a_ed     a_eps    b        beta     c        c_k      dbx      dc       delta_bx delta_c
                    delta_k  delta_sig         dp       el       eps      f1       g        i_no     lambda_k ll_for_prover_setup        mu_eps
                    mu_p     mu_teta  n        nu       psi      r        rbx      rc       re_bx    ro       str      str1     teta     _alfa)
  (setq ll_for_prover_setup
         '(("f_pr-dc" "1.")
           ("f_pr-dbx" "0.5")
           ("f_pr-n" "2")
           ("f_pr-r" "2.5")
           ("f_pr-beta" "90.0")
           ("f_pr-psi" "60.0")
           ("f_pr-dp" "30.0")
           ("f_pr-ro" "835.0")
           ("f_pr-nu" "3.0")))
  (setq str "Data Save RUn Load PRint EXit")
  (setvar "cmdecho" 0)
  (setq str1 "")
  (while (/= str1 "EXit")
    (initget str)
    (setq str1 (getkword (strcat "\n" str " : ")))
    (cond ((= str1 "Save")
           (setq fn (getfiled "Открытие файла с исходными данными по форсунке" "" "dat" 1))
           (if (null fn)
             (setq fn "data.dat"))
           (setq f1 (open fn "w"))
           (if (null f1)
             (progn (alert (princ (strcat "\nНе могу открыть файл: " fn ".\n"))) (exit)))
           (mapcar '(lambda (el) (print_file el f1)) '(dc dbx r ro dp beta nu c n psi))
           (close f1))
          ((= str1 "Load")
           (setq fn (getfiled "Открытие файла с исходными данными по форсунке" "" "dat" 0))
           (if (null fn)
             (setq fn "data.dat"))
           (load fn)
           (setq ll_for_prover_setup
                  (list (list "f_pr-dc" (rtos (* dc 1000.0)))
                        (list "f_pr-dbx" (rtos (* dbx 1000.0)))
                        (list "f_pr-n" (rtos n))
                        (list "f_pr-r" (rtos (* r 1000.0)))
                        (list "f_pr-beta" (angtos beta))
                        (list "f_pr-psi" (rtos psi))
                        (list "f_pr-dp" (rtos (* dp 0.00001)))
                        (list "f_pr-ro" (rtos ro))
                        (list "f_pr-nu" (rtos (* nu 1000000.0))))))
          ((= str1 "RUn")
           (setq i_no 0)
           (while (<= i_no 10)
             (princ "\n\t\t\t")
             (princ i_no)
             (setq rc        (f_dr dc)
                   rbx       (f_dr dbx)
                   b         (/ r rbx)
                   eps       (half_div b_g eps_g (/ 1.0 b))
                   a_eps     (/ (* r rc (sin beta)) (* eps n rbx rbx))
                   mu_eps    (cond ((= 0 i_no) (half_div a_g mu_g a_eps))
                                   ((> i_no 0) mu_p))
                   alfa_eps  (cond ((= 0 i_no) (half_div a_g alfa_g a_eps))
                                   ((> i_no 0) alfa_p))
                   g         (* pi 0.25 dc dc mu_eps (sqrt (* 2.0 ro dp)))
                   re_bx     (f_rebx g ro nu dbx n)
                   lambda_k  (half_div rebx_g lambdak_g (/ (log re_bx) (log 10.)))
                   c         (/ r rc)
                   c_k       (f_ck c rbx rc)
                   teta      (* lambda_k 0.5 a_eps (- c_k 1))
                   a_ed      (/ a_eps (+ 1 teta))
                   mu_teta   (half_div a_g mu_g a_ed)
                   alfa_teta (half_div a_g alfa_g a_ed)
                   _alfa     (half_div teta_g _alfa_g teta)
                   alfa_p    (* _alfa alfa_teta)
                   delta_bx  (f_deltabx re_bx n rc rbx)
                   delta_c   (f_deltac a_eps psi)
                   delta_k   (f_deltak lambda_k c_k a_eps)
                   delta_sig (+ delta_bx delta_k delta_c)
                   mu_p      (/ mu_teta (sqrt (+ 1 (* delta_sig mu_teta mu_teta))))
                   i_no      (1+ i_no))
             (foreach @n '(alfa_eps alfa_p mu_eps mu_p) (princ "\n") (princ @n) (princ " = ") (prin1 (eval @n)))))
          ((= str1 "Data") (for_prover:data))
          ((= str1 "PRint")
           (foreach @n  '(dc dbx r beta n psi ro dp nu g alfa_p mu_p)
             (princ "\n")
             (princ @n)
             (princ " = ")
             (prin1 (eval @n))))))
  (setvar "cmdecho" 1)
  (princ))


(defun for_prover:data  (/ act dcl_id ll_for_prover)
  (setq ll_for_prover ll_for_prover_setup)
  (setq dcl_id (load_dialog (findfile (utils:path-src-lsp "for_lic/for_lic-prover.dcl"))))
  (if (< dcl_id 0)
    (exit))
  (if (not (new_dialog "for_prover" dcl_id))
    (exit))
  (for_prover:setup)
  (for_prover:ac_tile)
  (setq act (start_dialog))
  (cond ((= act 0) (for_prover:cancel))
        ((= act 1) (for_prover:ok)))
  (unload_dialog dcl_id))


(defun for_prover:err (msg) (setvar "cmdecho" 1) (princ))


(defun for_prover:setup  ()
  (mapcar '(lambda (el)
             (cond ((= 2 (length el)) (set_tile (car el) (cadr el)))
                   ((= 3 (length el))
                    (start_list (car el))
                    (mapcar (function add_list) (caddr el))
                    (end_list)
                    (set_tile (car el) (cadr el)))))
          ll_for_prover)
  (start_image "f_pr-image")
  (fill_image 0 0 (dimx_tile "f_pr-image") (dimy_tile "f_pr-image") 250)
  (slide_image
    0
    0
    (dimx_tile "f_pr-image")
    (dimy_tile "f_pr-image")
    (findfile (utils:path-src-lsp "for_lic/for.sld")))
  (end_image))

(defun for_prover:ac_tile  ()
  (mapcar (function (lambda (el) (action_tile (car el) "(for_prover-all_ac)"))) ll_for_prover))

(defun for_prover-all_ac  ()
  (setq ll_for_prover
         (mapcar (function (lambda (el)
                             (cond ((= 2 (length el)) (list (car el) (get_tile (car el))))
                                   ((= 3 (length el)) (list (car el) (get_tile (car el)) (caddr el))))))
                 ll_for_prover))
  (for_prover:validate)
  (for_prover:setup))

(defun for_prover:validate () (princ "for_prover-validate"))

(defun for_prover:cancel () (princ "for_prover:cancel"))

(defun for_prover:ok  ()
  (princ "for_prover:ok")
  (setq dc   (* 0.001 (atof (cadr (assoc "f_pr-dc" ll_for_prover))))
        dbx  (* 0.001 (atof (cadr (assoc "f_pr-dbx" ll_for_prover))))
        n    (atof (cadr (assoc "f_pr-n" ll_for_prover)))
        r    (* 0.001 (atof (cadr (assoc "f_pr-r" ll_for_prover))))
        beta (angtof (cadr (assoc "f_pr-beta" ll_for_prover)))
        psi  (atof (cadr (assoc "f_pr-psi" ll_for_prover)))
        ro   (atof (cadr (assoc "f_pr-ro" ll_for_prover)))
        dp   (* 100000. (atof (cadr (assoc "f_pr-dp" ll_for_prover))))
        nu   (* 0.000001 (atof (cadr (assoc "f_pr-nu" ll_for_prover)))))
  (setq ll_for_prover_setup ll_for_prover))
