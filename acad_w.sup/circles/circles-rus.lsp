(setq *circles-command-list* '("c_r" "c_d" "cl_s" "ax_c" "ax_a" "ax_ca" "c_axis" "p_axis" "c_el" "cl_els" "c_ex" "c_sc" "c_123"))
;;;; (opech_cmds-str *circles-command-list*)

(defun c:с_к() (c:c_r))
(defun c:с_в() (c:c_d))
(defun c:сд_ы() (c:cl_s))
(defun c:фч_с() (c:ax_c))
(defun c:фч_ф() (c:ax_a))
(defun c:фч_сф() (c:ax_ca))
(defun c:с_фчшы() (c:c_axis))
(defun c:з_фчшы() (c:p_axis))
(defun c:с_уд() (c:c_el))
(defun c:сд_уды() (c:cl_els))
(defun c:с_уч() (c:c_ex))
(defun c:с_ыс() (c:c_sc))
(defun c:с_123() (c:c_123))

(princ "Loaded project circles.\n")
