;;;;;;("c_ex" "Построение сопряжения двух окружностей большим радиусом." "Отверстия")
(defun c:c_ex  (/ rad c1 r1 c2 r2 en_c1 en_c2)
  (setq rad (GETDIST "Введите радиус:")
        c1  (entget (car (entsel "Окружность:")))
        r1  (cdr (assoc 40 c1))
        c2  (entget (car (entsel "Окружность:")))
        r2  (cdr (assoc 40 c2))
        c1  (list (cons 0 "CIRCLE") (assoc 10 c1) (cons 40 (abs (- rad r1))) (cons 62 55))
        c2  (list (cons 0 "CIRCLE") (assoc 10 c2) (cons 40 (abs (- rad r2))) (cons 62 55)))
  (entmake c1)
  (setq en_c1 (entlast))
  (entmake c2)
  (setq en_c2 (entlast))
  (command "_circle" pause rad)
  (command "_erase" en_c1 en_c2 ""))

;;;("c_sc" "Масштабирование окружности, путем задания центра масштабирования
;;; и ее итогового радиуса.")
(defun c:c_sc  (/ ed rad echo PT)
  (setq ed  (entget (car (entsel "Окружность:")))
        rad (cdr (assoc 40 ed))
        pt  (getpoint "Точка масштабирования:"))
  (princ (strcat "\nСтарый радиус =" (rtos rad) "\n"))
  (setq echo (getvar "cmdecho"))
  (setvar "cmdecho" 0)
  (getvar "cmdech")
  (command "_scale" (cdr (assoc -1 ed)) "" "_non" pt "_r" rad pause)
  (setvar "cmdecho" echo))

(defun p-mid (p1 p2) (mapcar (function (lambda (el_1 el_2) (* 0.5 (+ el_1 el_2)))) p1 p2))

(defun p-perp (p1 p2) (polar (p-mid p1 p2) (+ (* 0.5 pi)(angle p1 p2)) (distance p1 p2)))


(defun in-triang-cen-rad  (p1 p2 p3 / P12 P12-P P23 P23-P PC RAD)
  (setq p12   (p-mid p1 p2)
        p23   (p-mid p2 p3)
        p12-p (p-perp p1 p2)
        p23-p (p-perp p2 p3)
        pc    (inters p12 p12-p p23 p23-p nil)
        rad   (distance pc p3))
  (list pc rad))
  

(defun c:c_123  (/ p1 p2 p3 ED I P-END P-RAD P-ST P0 P_I_C R0 R_I_C SS)
  (setq p1 (getpoint "Enter p1:")
        p2 (getpoint "Enter p2:")
        p3 (getpoint "Enter p3:"))
  (setq p-rad (in-triang-cen-rad p1 p2 p3)
        p0    (car p-rad)
        r0    (cadr p-rad))
  (dr:circle p0 r0 256)
  (prompt "Select circles or arcs:")
  (setq ss (ssget)
        i  (sslength ss))
  (while (<= 0 (setq i (1- i)))
    (setq ed    (entget (ssname ss i))
          p_i_c (dxf-get 10 ed)
          r_i_c (dxf-get 40 ed)
          p-st  (polar p_i_c (angle p_i_c p0) r_i_c)
          p-end (polar p_i_c (angle p0 p_i_c) r_i_c))
    (dr:line p-st p-end 256)))
