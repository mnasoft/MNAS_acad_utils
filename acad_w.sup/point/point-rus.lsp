(setq *point-command-list* '("pd" "xy" "xy_sc" "rot_p"))
;;;; (opech_cmds-str *point-command-list*)

(defun c:çâ() (c:pd))
(defun c:÷í() (c:xy))
(defun c:÷í_ûñ() (c:xy_sc))
(defun c:êùå_ç() (c:rot_p))

(princ "Loaded project point.\n")
