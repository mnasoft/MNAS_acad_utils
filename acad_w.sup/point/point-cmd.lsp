;;;;;;("pd" "Настройка размеров и стиля отображения точки." "Настройка")
(defun c:pd () (command "pdmode" "35") (command "pdsize" "2"))

;;;;;;("xy" "Точка по приращениям." "Точки")
(defun c:xy  (/ p0 p1 dir_0 dx dy p3)
  (setq p0 (getpoint "\nБазовая точка:"))
  (setq p1 (getpoint p0 "\nНаправление:"))
  (setq dir_0 (angle p0 p1))
  (setq dx (getreal "\nПриращение по X:"))
  (setq dy (getreal "\nПриращение по Y:"))
  (setq p3 (dxdy p0 dx dy dir_0))
  (command "_point" "_non" p3)
  (setq p3 p3))

;;;;;;("xy_sc" "Точка по приращениям и масштабам." "Точки")
(defun c:xy_sc  (/ dir_0 dx dy p0 p1 p3 scx scy)
  (setq p0 (getpoint "\nБазвоая точка:"))
  (setq p1 (getpoint p0 "\nНаправление:"))
  (setq dir_0 (angle p0 p1))
  (setq dx (getreal "\nПриращение по X:"))
  (setq dy (getreal "\nПриращение по Y:"))
  (setq scx (getreal "\nМасштаб по X:"))
  (setq scy (getreal "\nМасштаб по Y:"))
  (setq p3 (dxdy_sc_xy p0 dx dy scx scy dir_0))
  (command "_point" "_non" p3)
  (setq p3 p3))

;;;;;;("rot_p" "Точка повернутая с масштабом." "Точки")
(defun c:rot_p  (/ p0 p1 point alfa dir_0 sc p3)
  (setq p0 (getpoint "\nБазовая точка:"))
  (setq p1 (getpoint p0 "\nНаправление:"))
  (setq point (getpoint p0 "\nТчка для поворота:"))
  (setq alfa (getangle "Угол поворота:"))
  (setq dir_0 (angle p0 p1))
  (setq sc (getreal "\nМасштаб :"))
  (setq p3 (rotate_sc p0 point alfa sc))
  (command "_point" "_non" p3)
  (setq p3 p3))
