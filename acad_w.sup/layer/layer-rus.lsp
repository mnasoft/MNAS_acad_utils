(setq *layer-command-list*
       '("lay" "rgb" "la_dhv" "bl_off" "bl_fr" "bl_all_on" "bl_all_th" "vl_s_d" "cl_s_d" "cl_sw_d" "ml_off" "ml_on"
         "ml_on_c" "ml_off_c" "am_la" "vl_fr" "vl_th" "vl_fr_w" "vl_th_all" "vl_fr_w+_d" "sl_on" "sl_off" "sl_th"
         "sl_fr" "sl_lo" "sl_un" "svl_th" "svl_fr" "llay"))
;;;; (opech_cmds-str *layer-command-list*)

(defun c:дфн() (c:lay))
(defun c:кпи() (c:rgb))
(defun c:дф_врм() (c:la_dhv))
(defun c:ид_щаа() (c:bl_off))
(defun c:ид_ак() (c:bl_fr))
(defun c:ид_фдд_щт() (c:bl_all_on))
(defun c:ид_фдд_ер() (c:bl_all_th))
(defun c:мд_ы_в() (c:vl_s_d))
(defun c:сд_ы_в() (c:cl_s_d))
(defun c:сд_ыц_в() (c:cl_sw_d))
(defun c:ьд_щаа() (c:ml_off))
(defun c:ьд_щт() (c:ml_on))
(defun c:ьд_щт_с() (c:ml_on_c))
(defun c:ьд_щаа_с() (c:ml_off_c))
(defun c:фь_дф() (c:am_la))
(defun c:мд_ак() (c:vl_fr))
(defun c:мд_ер() (c:vl_th))
(defun c:мд_ак_ц() (c:vl_fr_w))
(defun c:мд_ер_фдд() (c:vl_th_all))
(defun c:мд_ак_ц+_в() (c:vl_fr_w+_d))
(defun c:ыд_щт() (c:sl_on))
(defun c:ыд_щаа() (c:sl_off))
(defun c:ыд_ер() (c:sl_th))
(defun c:ыд_ак() (c:sl_fr))
(defun c:ыд_дщ() (c:sl_lo))
(defun c:ыд_гт() (c:sl_un))
(defun c:ымд_ер() (c:svl_th))
(defun c:ымд_ак() (c:svl_fr))
(defun c:ддфн() (c:llay))

(princ "Loaded project layer.\n")
