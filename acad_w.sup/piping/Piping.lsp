;;;;;;("pipe" "Построение трубопровода по точкам." "not defined")
(defun c:pipe  (/        a        center   center_1 e        el_1     el_2     en_c0    en_c1    half_1   half_2   l        ort      p0
                p0_n     p0_new   p1       p1_n     p1_new   p1_new_1 p2       p2_n     p2_new   p3       p3_n     p3_new   p3_new_3 pla_1
                pla_2    pla_3    pla_4    r0       r1       r3       sp       sp_1     sp_2     echo     delobj   en_line_01        en_line_12
                en_line_23)
  (setq echo (getvar "cmdecho"))
  (setvar "cmdecho" 0)
  (command "ucs" "")
  (setq p0 (getpoint "\nВведите начальную точку на оси:"))
  (setq p1 (getpoint p0 "\nВведите первую точку излома оси:"))
  (setq sp (list (cons 0 "line") (cons 10 p0) (cons 11 p1) (cons 62 3)))
  (entmake sp)
  (setq en_line_01 (entlast))
  (setq p3 (getpoint p1 "\nВведите вторую точку излома оси:"))
  (setq sp_2 (list (cons 0 "line") (cons 10 p1) (cons 11 p3) (cons 62 3)))
  (entmake sp_2)
  (setq en_line_12 (entlast))
  (setq p2 (getpoint p3 "\nВведите конечную точку на оси выхода: "))
  (setq sp_1 (list (cons 0 "line") (cons 10 p2) (cons 11 p3) (cons 62 3)))
  (entmake sp_1)
  (setq en_line_23 (entlast))
  (setq r3 (* 1.0 (getdist "\nВведите радиус трубки: ")))
  (setq r0 (getdist "\nВведите первый радиус скругления трубки: "))
  (setq r1 (getdist "\nВведите второй радиус скругления трубки: "))
  (setq a t)
  (while a
    (command "ucs" "n" "3p" p0 p1 p3)   ;Первая часть полилинии
    (setq p0_new (trans p0 0 1))
    (setq p1_new (trans p1 0 1))
    (setq p0_n (list (car p0_new) (+ (cadr p0_new) r0) 0.0))
    (setq p1_n (list (car p1_new) (+ (cadr p1_new) r0) 0.0))
    (command "ucs" "")
    (command "ucs" "n" "3p" p3 p1 p0)
    (setq p3_new (trans p3 0 1))
    (setq p1_new_1 (trans p1 0 1))
    (setq p3_new (list (car p3_new) (+ (cadr p3_new) r0) 0.0))
    (setq p1_new_1 (list (car p1_new_1) (+ (cadr p1_new_1) r0) 0.0))
    (setq p3_new (trans p3_new 1 0))
    (setq p1_new_1 (trans p1_new_1 1 0))
    (command "ucs" "")
    (command "ucs" "n" "3p" p0 p1 p3)
    (setq p3_new (trans p3_new 0 1))
    (setq p1_new_1 (trans p1_new_1 0 1))
    (setq center (inters p0_n p1_n p3_new p1_new_1 nil))
    (if (< (car center) 0)
      (progn (setq r0 (getreal (strcat "\nСкругление радиусом " (rtos r0) " невозможно. Задайте новый радиус: ")))
             (command "ucs" ""))
      (setq a nil)))
  (setq pla_1 (list (car center) 0.0))
  (setq center (trans center 1 0))
  (command "ucs" "")
  (command "ucs" "n" "3p" p3 p1 p0)
  (setq center (trans center 0 1))
  (setq pla_2 (trans (list (car center) 0.0) 1 0))
  (command "ucs" "")
  (command "ucs" "n" "3p" p0 p1 p3)
  (setq pla_2 (trans pla_2 0 1))
  (command "pline" "non" p0_new "non" pla_1 "a" "r" r0 "non" pla_2 "")
  (setq el_1 (entlast))
  (setq pla_2 (trans pla_2 1 0))
  (setq a t)
  (while a
    (command "ucs" "")                  ;Вторая часть полилинии
    (command "ucs" "n" "3p" p2 p3 p1)
    (setq p2_new (trans p2 0 1))
    (setq p3_new (trans p3 0 1))
    (setq p2_n (list (car p2_new) (+ (cadr p2_new) r1) 0.0))
    (setq p3_n (list (car p3_new) (+ (cadr p3_new) r1) 0.0))
    (command "ucs" "")
    (command "ucs" "n" "3p" p1 p3 p2)
    (setq p1_new (trans p1 0 1))
    (setq p3_new_3 (trans p3 0 1))
    (setq p1_new (list (car p1_new) (+ (cadr p1_new) r1) 0.0))
    (setq p3_new_3 (list (car p3_new_3) (+ (cadr p3_new_3) r1) 0.0))
    (setq p1_new (trans p1_new 1 0))
    (setq p3_new_3 (trans p3_new_3 1 0))
    (command "ucs" "")
    (command "ucs" "n" "3p" p2 p3 p1)
    (setq p1_new (trans p1_new 0 1))
    (setq p3_new_3 (trans p3_new_3 0 1))
    (setq center_1 (inters p2_n p3_n p1_new p3_new_3))
    (if (< (car center_1) 0)
      (progn (setq r1 (getreal (strcat "\nСкругление радиусом " (rtos r1) " невозможно. Задайте новый радиус: ")))
             (command "ucs" ""))
      (setq a nil)))
  (setq pla_3 (list (car center_1) 0.0 0.0))
  (setq center_1 (trans center_1 1 0))
  (command "ucs" "")
  (command "ucs" "n" "3p" p1 p3 p2)
  (setq center_1 (trans center_1 0 1))
  (setq pla_4 (trans (list (car center_1) 0.0 0.0) 1 0))
  (setq center_1 (trans center_1 1 0))
  (command "ucs" "")
  (command "ucs" "n" "3p" p2 p3 p1)
  (setq pla_4 (trans pla_4 0 1))
  (setq pla_2 (trans pla_2 0 1))
  (command "pline" "non" p2_new "non" pla_3 "a" "r" r1 "non" pla_4 "l" "non" pla_2 "")
  (setq el_2 (entlast))                 ;Первая часть трубки
  (command "ucs" "")
  (command "ucs" "n" "3p" p0 p1 p3)
  (command "ucs" "y" "90")
  (command "circle" "non" '(0.0 0.0) r3)
  (setq en_c0 (entlast))
  (command "extrude" en_c0 "" "p" el_1)
  (setq half_1 (entlast))               ;Вторая часть трубки
  (command "ucs" "")
  (command "ucs" "n" "3p" p2 p3 p1)
  (command "ucs" "y" "90")
  (command "circle" "non" '(0.0 0.0) r3)
  (setq en_c1 (entlast))
  (command "extrude" en_c1 "" "p" el_2)
  (setq half_2 (entlast))
  (command "union" half_1 half_2 "")
  (command "ucs" "")
  (if (= (getvar "delobj") 1)
    (command "erase" en_line_01 en_line_12 en_line_23 el_1 el_2 ""))
  (setvar "cmdecho" echo))
