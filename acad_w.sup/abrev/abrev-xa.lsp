;;;;;;("xa" "Выполняет рекурсивный взрыв блоков" "Аббревиатуры")
(defun c:xa  (/ el ss)
  (entmake '((0 . "POINT") (10 0.0 0.0 0.0)))
  (setq el (entlast))
  (prompt "Выберите объекты для полного взрыва")
  (setq ss (ssget '((0 . "INSERT"))))
  (while (and ss (> (sslength ss) 0))
    (explode-all ss)
    (setq ss (select-all-past-ename el))
    )
  (entdel el)
  (princ))

(defun select-all-past-ename  (el / ss ed)
  (setq ss (ssadd))
  (while (and el (setq el (entnext el)))
    (setq ed (entget el))
    (if (= "INSERT" (cdr (assoc 0 ed)))
    (setq ss (ssadd el ss))))
  ss)

(defun explode-all  (ss / i)
  (setq i (sslength ss))
  (while (>= (setq i (1- i)) 0) (vl-cmdf "_.explode" (ssname ss i) "")))
