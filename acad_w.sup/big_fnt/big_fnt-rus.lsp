(setq *big_fnt-command-list* '("draw_font" "ins_lit"))
;;;; (opech_cmds-str *big_fnt-command-list*)

(defun c:âêôö_àùòå() (c:draw_font))
(defun c:øòû_äøå() (c:ins_lit))

(princ "Loaded project big_fnt.\n")
