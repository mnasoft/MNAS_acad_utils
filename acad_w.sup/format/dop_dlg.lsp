(setq
  dop_dlg_registry
   '(
     (dsht_1_val
      (("Специф_посл"	((2 . "/Format/speciph_n.dwg")	 (70 . 3)	 (11 20.0 20.0 0.0)	 (12 205.0 20.0 0.0)	 (13 205.0 292.0 0.0)	 (14 20.0 292.0 0.0)	)       )
       ("Специф_1"	((2 . "/Format/speciph_1.dwg")	 (70 . 3)	 (11 20.0 45.0 0.0)	 (12 205.0 45.0 0.0)	 (13 205.0 292.0 0.0)	 (14 20.0 292.0 0.0)	)       )
       ("Л.рег.изм"	((2 . "/FORMAT/DOP_PRM.DWG")	 (70 . 0)	 (11 -190.0 282.0 0.0)	 (12 -190.0 20.0 0.0)	 (13 -5.0 20.0 0.0)	 (14 -5.0 292.0 0.0)	)       )
       ("Тех.мет.вед"	((2 . "/FORMAT/DOP_TMV.DWG")	 (70 . 3)	 (11 0.0 5.0 0.0)	 (12 8.0 5.0 0.0)	 (13 8.0 115.0 0.0)	 (14 0.0 115.0 0.0)	)       )
       ("Гр. л.верх"	((2 . "/FORMAT/DOP_G_LT.DWG")	 (70 . 2)	 (11 20.0 -27.0 0.0)	 (12 160.0 -27.0 0.0)	 (13 160.0 -5.0 0.0)	 (14 20.0 -5.0 0.0)	)       )
       ("Гр.прав.низ."	((2 . "/FORMAT/DOP_G_RB.DWG")	 (70 . 0)	 (11 -125.0 60.0 0.0)	 (12 -5.0 60.0 0.0)	 (13 -5.0 68.0 0.0)	 (14 -125.0 68.0 0.0)	)       )
       ("Текст.доп"	((2 . "/FORMAT/DOP_TEXT.DWG")	 (70 . 0)	 (11 -125.0 45.0 0.0)	 (12 -5.0 45.0 0.0)	 (13 -5.0 68.0 0.0)	 (14 -125.0 68.0 0.0)	)       )
       ("Перв.прим"	((2 . "/FORMAT/DOP_PRIM.DWG")	 (70 . 3)	 (11 8.0 182.0 0.0)	 (12 20.0 182.0 0.0)	 (13 20.0 292.0 0.0)	 (14 8.0 292.0 0.0)	)       )
       ("Архив"	        ((2 . "/FORMAT/DOP_ARH.DWG")	 (70 . 3)	 (11 8.0 5.0 0.0)	 (12 20.0 5.0 0.0)	 (13 20.0 155.0 0.0)	 (14 8.0 155.0 0.0)	)       )
      )
     )
     (dsht_1_no 7)
     (dsht_2_val
      (("Гр. л.верх"	((2 . "/FORMAT/DOP_G_LT.DWG")	 (70 . 2)	 (11 20.0 -27.0 0.0)	 (12 160.0 -27.0 0.0)	 (13 160.0 -5.0 0.0)	 (14 20.0 -5.0 0.0)	)       )
       ("Гр.прав.низ."	((2 . "/FORMAT/DOP_G_RB.DWG")	 (70 . 0)	 (11 -125.0 60.0 0.0)	 (12 -5.0 60.0 0.0)	 (13 -5.0 68.0 0.0)	 (14 -125.0 68.0 0.0)	)       )
       ("Архив"	        ((2 . "/FORMAT/DOP_ARH.DWG")	 (70 . 3)	 (11 8.0 5.0 0.0)	 (12 20.0 5.0 0.0)	 (13 20.0 155.0 0.0)	 (14 8.0 155.0 0.0)	)       )
       ("Тех.мет.вед"	((2 . "/FORMAT/DOP_TMV.DWG")	 (70 . 3)	 (11 0.0 5.0 0.0)	 (12 8.0 5.0 0.0)	 (13 8.0 115.0 0.0)	 (14 0.0 115.0 0.0)	)       )
       ("Перв.прим"	((2 . "/FORMAT/DOP_PRIM.DWG")	 (70 . 3)	 (11 8.0 182.0 0.0)	 (12 20.0 182.0 0.0)	 (13 20.0 292.0 0.0)	 (14 8.0 292.0 0.0)	)       )
      )
     )
     (dsht_2_no nil)
     (dsht_3_val
      (("Гр. л.верх"	((2 . "/FORMAT/DOP_G_LT.DWG")	 (70 . 2)	 (11 20.0 -27.0 0.0)	 (12 160.0 -27.0 0.0)	 (13 160.0 -5.0 0.0)	 (14 20.0 -5.0 0.0)	)       )
       ("Гр.прав.низ."	((2 . "/FORMAT/DOP_G_RB.DWG")	 (70 . 0)	 (11 -125.0 60.0 0.0)	 (12 -5.0 60.0 0.0)	 (13 -5.0 68.0 0.0)	 (14 -125.0 68.0 0.0)	)       )
       ("Архив"	        ((2 . "/FORMAT/DOP_ARH.DWG")	 (70 . 3)	 (11 8.0 5.0 0.0)	 (12 20.0 5.0 0.0)	 (13 20.0 155.0 0.0)	 (14 8.0 155.0 0.0)	)       )
       ("Тех.мет.вед"	((2 . "/FORMAT/DOP_TMV.DWG")	 (70 . 3)	 (11 0.0 5.0 0.0)	 (12 8.0 5.0 0.0)	 (13 8.0 115.0 0.0)	 (14 0.0 115.0 0.0)	)       )
       ("Перв.прим"	((2 . "/FORMAT/DOP_PRIM.DWG")	 (70 . 3)	 (11 8.0 182.0 0.0)	 (12 20.0 182.0 0.0)	 (13 20.0 292.0 0.0)	 (14 8.0 292.0 0.0)	)       )
      )
     )
    )
)


(defun dop_ac_1 (value) (setq dsht_1_no (atoi value)))

(defun dop_ac_2 (value) (setq dsht_2_no (atoi value)))

(defun dop_ac_3	()
  (if dsht_1_no
    (progn
      (setq str1 (car (setq ll1 (nth dsht_1_no dsht_1_val))))
      (if (null (assoc str1 dsht_2_val))
	(setq dsht_2_val (cons ll1 dsht_2_val))
      )
    )
  )
)

(defun dop_ac_4	(/ str1 ll1 ll2)
  (if dsht_2_no
    (progn
      (setq str1 (car (nth dsht_2_no dsht_2_val)))
      (while (setq ll2 (car dsht_2_val))
	(setq dsht_2_val (cdr dsht_2_val))
	(if (/= str1 (car ll2))
	  (setq ll1 (cons ll2 ll1))
	)
      )
      (setq dsht_2_val
	     (reverse ll1)
	    dsht_2_no nil
      )
    )
  )
)

(defun c__out
	      (/ ss1 f1 i1 en1 ed1 old_err p0 j1 p1 p2 p3 p4 str1 str2 ll)
  (while (not (setq ss1 (ssget))))
  (setq i1 (sslength ss1))
  (while
    (not (setq str1 (getstring "\nВведите название штампа:")))
  )
  (while (not (setq str2 (getfiled "Выбор файла для хранения штампа" "" "dwg" 1))))
  (initget "LB LT RB RT")
  (setq wo (getkword "LB LT RB RT<LB>:"))
  (cond
    ((or (= wo "LB") (= wo nil)) (setq j1 3))
    ((= wo "LT") (setq j1 2))
    ((= wo "RB") (setq j1 0))
    ((= wo "RT") (setq j1 1))
  )
  (princ j1)
  (while (not (setq p0 (getpoint "\nВведите базовую точку:")))  )
  (while (not (setq p1 (getpoint "\nПервая точка зоны ограничивающая штамп:"))))
  (while (not (setq p2 (getpoint "\nВторая точка зоны ограничивающая штамп:"))))
  (while (not (setq p3 (getpoint "\nТретья точка зоны ограничивающая штамп:"))))
  (while (not (setq p4 (getpoint "\nЧетвертая точка зоны ограничивающая штамп:"))))
  (setq
    p1 (mapcar '- p1 p0)
    p2 (mapcar '- p2 p0)
    p3 (mapcar '- p3 p0)
    p4 (mapcar '- p4 p0)
  )
  (setq	ll
	 (list str1
	       (list
		 (cons 2 str2)
		 (cons 70 j1)
		 (cons 11 p1)
		 (cons 12 p2)
		 (cons 13 p3)
		 (cons 14 p4)
	       )
	 )
  )
  (setvar "expert" 5)
  (command "_wblock" str2 "" p0 ss1 "")
  (setvar "expert" 0)
  (setq dsht_1_val (cons ll dsht_1_val))
  (princ)
)

(defun dop_ac_6	(/ str1 ll1 ll2)
  (if dsht_1_no
    (progn
      (setq str1 (car (nth dsht_1_no dsht_1_val)))
      (while (setq ll2 (car dsht_1_val))
	(setq dsht_1_val (cdr dsht_1_val))
	(if (/= str1 (car ll2))
	  (setq ll1 (cons ll2 ll1))
	)
      )
      (setq dsht_1_val
	     (reverse ll1)
	    dsht_1_no nil
      )
    )
  )
)


(defun dop_dlg (/ dop_dlg_ok f_n action f1 str1 ll1 do_dialog dcl_id)
  (load_format_dcl)
  (setq do_dialog t)
  (reg_read_default_lst reg_root dop_dlg_registry)
  ;(reg_read_lst reg_root dop_dlg_registry)
  (while do_dialog
    (if	(not (new_dialog "dop_dlg" dcl_id))
      (exit)
    )
    (if	dsht_1_val
      (progn
	(start_list "dop_dlg_1")
	(mapcar 'add_list (mapcar 'car dsht_1_val))
	(end_list)
      )
    )
    (if	dsht_2_val
      (progn
	(start_list "dop_dlg_2")
	(mapcar 'add_list (mapcar 'car dsht_2_val))
	(end_list)
      )
    )
    (if	dsht_1_no
      (set_tile "dop_dlg_1" (rtos dsht_1_no))
    )
    (if	dsht_2_no
      (set_tile "dop_dlg_2" (rtos dsht_2_no))
    )

    (action_tile "dop_dlg_1" "(dop_ac_1 $value)")
    (action_tile "dop_dlg_2" "(dop_ac_2 $value)")
    (action_tile "dop_dlg_3" "(done_dialog 4)")
    (action_tile "dop_dlg_4" "(done_dialog 5)")
    (action_tile "dop_dlg_5" "(done_dialog 2)")
    (action_tile "dop_dlg_6" "(done_dialog 6)")
    (action_tile "dop_dlg_7" "(done_dialog 7)")

    (dop_ac_4)

    (setq action (start_dialog))
    (cond
      (
       (= action 1) ;ok
       (setq dsht_3_val dsht_2_val)
       ;(reg_write_default_lst reg_root dop_dlg_registry) ; По просьбе Давлеткужина
       (reg_write_lst reg_root dop_dlg_registry); По просьбе Давлеткужина
       (setq do_dialog nil)
      )
      ((= action 0) (setq do_dialog nil))
      ((= action 2) (c__out))
      ((= action 3) (ed_4_do) (setq do_dialog nil))
      ((= action 4) (dop_ac_3))
      ((= action 5) (dop_ac_4))
      ((= action 6) (dop_ac_6))
      (
       (= action 7)
       (if
	 (and dsht_1_no dsht_1_val)
	  (progn
	    (setq d7 (nth dsht_1_no dsht_1_val))
	    (add_dop_sht_dlg)
	  )
       )
      )
    )
  )
  (unload_dialog dcl_id)
  (princ)
)    ;defun dop_dlg
;|«Visual LISP© Format Options»
(130 2 5 2 nil "end of" 100 9 0 0 0 T T nil T)
;*** DO NOT add text below the comment! ***|;
