;;;;;;("index_ru" "Переключает символы для баз, направлений взгляда и разрезов на русский алфавит." "Размеры")
(defun c:index_ru () (vlax-ldata-put "index" "abc" "ru"))
;;;;;;("index_en" "Переключает символы для баз, направлений взгляда и разрезов на английский алфавит." "Размеры" )
(defun c:index_en () (vlax-ldata-put "index" "abc" "en"))

;;;;;;("index" "Выводит на экран диалоговое окно, позволяющее задать символ и индекс для генерируемых впоследствии обозначений баз, направления взгляда, разреза." "Размеры")

(defun c:index  (/ dcl_id do_dialog ac index_A index_0)
  (setq dcl_id    (load_dialog (findfile "acad_w.sup/dims/abc.dcl"))
        do_dialog t)
  (while do_dialog
    (if (not (new_dialog "начальный_индекс" dcl_id))
      (exit))
    (action_tile "lb_1_1" "(index:ac:lb_1_1 $KEY $VALUE $DATA $REASON $X $Y)")
    (action_tile "lb_1_2" "(index:ac:lb_1_2 $KEY $VALUE $DATA $REASON $X $Y)")
    (action_tile "bt_1_1" "(print \"bt_1_1\")")
    (index:init)
    (setq ac (start_dialog))
    (cond ((= ac 0) (setq do_dialog nil))
          ((= ac 1) (index:ac_ok))))
  (unload_dialog dcl_id))

(defun index:ac_ok  ()
  (setq last_index (list index_A index_0)
        do_dialog  nil)
  (print last_index))

(defun index:init  (/ i)
  (vlax-ldata-get "index" "abc" "ru")
  (setq index_A (1- (car (index:getlast)))
        index_0 (cadr (index:getlast)))
  (start_list "lb_1_1")
  (mapcar (function add_list) (index:str->list_sym))
  (end_list)
  (set_tile "lb_1_1" (itoa index_A))
  (start_list "lb_1_2")
  (setq i 0)
  (repeat 100 (add_list (itoa i)) (setq i (1+ i)))
  (end_list)
  (set_tile "lb_1_2" (itoa index_0)))

(defun index:str->list_sym  (/ len str sym sym_lst)
  (setq str (index:abc)
        len (index:abc_len))
  (while (>= len 1)
    (setq sym     (substr str len 1)
          sym_lst (cons sym sym_lst)
          len     (1- len)))
  sym_lst)
(defun index:ac:lb_1_1 ($KEY $VALUE $DATA $REASON $X $Y) (setq index_A (1+ (atoi $VALUE))))
(defun index:ac:lb_1_2 ($KEY $VALUE $DATA $REASON $X $Y) (setq index_0 (atoi $VALUE)))
