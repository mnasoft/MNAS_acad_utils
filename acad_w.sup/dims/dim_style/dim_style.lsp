(defun load_dim_vars (/ dim_var_lst)
  (setq
    dim_var_lst
     (list
       (list "DIMADEC" 0)		;DIMADEC Задает число точных знаков, отображаемых в угловых размерах. 
       (list "DIMALT" 0)		;DIMALT Управление альтернативными единицами в размерах. 
       (list "DIMALTD" 3)		;DIMALTD Задает число знаков после запятой в альтернативных единицах. Если системная переменная DIMALT включена, переменная DIMALTD задает количество знаков после запятой, отображаемых в альтернативных размерах.
       (list "DIMALTF" (/ 1.0 25.4))	;DIMALTF Задает множитель для альтернативных единиц. Если переменная DIMALT включена, переменная DIMALTF умножает линейные размеры на коэффициент для получения значения в альтернативной системе измерений. Начальное значение переменной равно числу миллиметров в одном дюйме.
       (list "DIMALTRND" 0.0)		;DIMALTRND Служит для округления альтернативных размерных единиц.
       (list "DIMALTTD" 4)		;DIMALTTD Задает число знаков после запятой в значениях допуска для альтернативных размерных единиц. 
       (list "DIMALTTZ" 0)		;DIMALTTZ Управляет подавлением нулей в значениях допуска. 
       (list "DIMALTU" 2)		;DIMALTU Задает формат альтернативных единиц для всех размерных субстилей, за исключением угловых.
       (list "DIMALTZ" 0)		;DIMALTZ Управляет подавлением нулей в альтернативных размерных единицах. Значения переменной DIMALTZ от 0 до 3 относятся только к размерам, выраженным в футах и дюймах.
					;DIMANNO Указывает, является ли текущий размерный стиль аннотативный .       
       (list "DIMAPOST" "")		;DIMAPOST Указывает префикс или суффикс текста (или и то, и другое) альтернативных размерных единиц для всех типов размеров, кроме угловых.
       (list "DIMARCSYM" 0)		;DIMARCSYM Управляет отображением обозначения дуги в размере длины дуги. 
;       (list "DIMASO" 1)
       (list "DIMASSOC" 2)		;DIMASSOC Управляет ассоциативностью размерных объектов и расчленением размеров.
       (list "DIMASZ" 5.0)		;DIMASZ Управляет величинами стрелок размерных линий и линий выносок. а также длинами полок выносок.		
       (list "DIMATFIT" 2)		;DIMATFIT Задает способ расположения размерного текста и стрелок, если и для текста, и для стрелок недостаточно места в выносных линиях.
       (list "DIMAUNIT" 1)		;DIMAUNIT Задает формат единиц измерения для угловых размеров.
       (list "DIMAZIN" 2)		;DIMAZIN Управляет подавлением нулей для всех угловых размеров.
       (list "DIMBLK" "")		;DIMBLK Задается блок стрелок, отображаемый на концах размерных линий. Для того чтобы вернуться к стандартным заполненным замкнутым стрелкам, следует ввести точку (.) . Ниже представлены элементы и имена блоков стрелок, используемых для выбора блоков в диалоговых окнах "Создание", "Редактирование" и "Переопределение размерного стиля". Разрешается также использовать в качестве стрелок пользовательские блоки.
       (list "DIMBLK1" "")		;DIMBLK1 Задает стрелку для первого конца размерной линии, если включена переменная DIMSAH. Для того чтобы вернуться к стандартным заполненным замкнутым стрелкам, следует ввести точку (.) . Полный список стрелок приведен в описании переменной DIMBLK.
       (list "DIMBLK2" "")		;DIMBLK2 Задает стрелку для второго конца размерной линии, если включена переменная DIMSAH. Для того чтобы вернуться к стандартным заполненным замкнутым стрелкам, следует ввести точку (.). Полный список стрелок приведен в описании переменной DIMBLK.
       (list "DIMCEN" 2.5)		;DIMCEN Управляет рисованием маркеров центра и центровых линий кругов и дуг с помощью команд РЗМЦЕНТР, РЗМДИАМЕТР и РЗМРАДИУС. В командах РЗМДИАМЕТР и РЗМРАДИУС можно нарисовать маркеры центра только в том случае, если размерная линия размещается за границами круга или дуги. 
       (list "DIMCLRD" 0)		;DIMCLRD Задает цвета размерных линий, стрелок и размерных линий выноски. Переменная также задает цвет линий выноски, создаваемых с помощью команды ВЫНОСКА. Номера цветов отображаются в диалоговом окне "Выбор цвета". Для задания значения "ПОБЛОКУ" введите 0. Для задания значения "ПОСЛОЮ" введите 256. 
       (list "DIMCLRE" 0)		;DIMCLRE Задает цвет для размерных выносных линий. Номера цветов отображаются в диалоговом окне "Выбор цвета". Для задания значения "ПОБЛОКУ" введите 0. Для задания значения "ПОСЛОЮ" введите 256.
       (list "DIMCLRT" 0)		;DIMCLRT Цвет, которым рисуется размерный текст. Можно присваивать переменной любой из допустимых номеров цветов. 
       (list "DIMDEC" 2)		;DIMDEC Задает число знаков после запятой, отображаемых для основных единиц размера. Точность представления основывается на выбранном формате единиц.
       (list "DIMDLE" 0.0)		;DIMDLE Задает значение расстояния, на которое размерная линия выступает за выносную линию, когда наклонные засечки рисуются вместо стрелок.
       (list "DIMDLI" 10.0)		;DIMDLI Управляет расстоянием между размерными линиями в базовых размерах. Каждая новая размерная линия смещается относительно предыдущей на заданное здесь число единиц. На уже имеющиеся размеры изменение DIMDLI никакого влияния не оказывает.
       (list "DIMDSEP" ",")		;DIMDSEP Задает символ десятичного разделителя, используемый при создании размеров с десятичным форматом единиц измерения.
       (list "DIMEXE" 1.5)		;DIMEXE Задает величину, на которую выносная линия должна выступать за размерную линию.
       (list "DIMEXO" 0.0)		;DIMEXO Задает величину смещения выносных линий относительно исходных точек. При использовании выносных линий фиксированной длины это значение определяет минимальную величину смещения.
       (list "DIMFIT" 2)		
       (list "DIMFRAC" 0)		;DIMFRAC Задает формат дроби, если переменная DIMLUNIT установлена в значение 4 (архитектурные) или 5 (дробные).
       (list "DIMFXL" 1.0)		;DIMFXL Установка полной длины выносных линий от размерной линии до исходной точки размера. Длина устанавливается в единицах чертежа.
       (list "DIMFXLON" 0)		;DIMFXLON Управляет установкой фиксированной длины выносных линий. Если переменная DIMFXLON включена, длина выносных линий задается переменной DIMFXL.
       (list "DIMGAP" 1.5)		;DIMGAP Задает зазор вокруг размерного текста при разрыве размерной линии в соответствии с размерным текстом. Также задает зазор между аннотацией и полкой выноски, созданной с помощью команды ВЫНОСКА. При задании отрицательного значения DIMGAP помещает размерный текст в рамку.
       (list "DIMJOGANG" 0.785398)	;DIMJOGANG Определяет угол пересекающегося сегмента размерной линии, представляющей собой ломаную линию размера радиуса. Ломаные линии размеров радиуса строятся в случаях, когда центр расположен за пределами страницы.
       (list "DIMJUST" 0)		;DIMJUST Управляет горизонтальным расположением размерного текста.
       (list "DIMLDRBLK" "")		;DIMLDRBLK Задает тип стрелки для выноски. Для того чтобы вернуться к стандартным заполненным замкнутым стрелкам, следует ввести точку (.). Полный список стрелок приведен в описании переменной DIMBLK.
       (list "DIMLFAC" 1.0)		;DIMLFAC Задает масштабный коэффициент для значений линейных размеров. Все измеренные расстояния (в т.ч. радиусы, диаметры и координаты) перед генерацией размерных текстов умножаются на этот коэффициент. Положительные значения переменной DIMLFAC используются для размеров в пространстве модели и в пространстве листа; отрицательные значения используются только в пространстве листа.
       (list "DIMLIM" 0)		;DIMLIM Задает ограничения размеров в качестве текста по умолчанию. Включение переменной DIMLIM приводит к автоматическому отключению переменной DIMTOL.
;;;	 (list "DIMLTEX1" "")		;DIMLTEX1 Установка типа первой выносной линии. Значением переменной могут быть BYLAYER, BYBLOCK или имя типа линии.
;;;	 (list "DIMLTEX2" "")		;DIMLTEX2 Установка типа второй выносной линии. Значением переменной могут быть BYLAYER, BYBLOCK или имя типа линии.
;;;	 (list "DIMLTYPE" "")		;DIMLTYPE Установка типа размерных линий. Значением переменной могут быть BYLAYER, BYBLOCK или имя типа линии.
       (list "DIMLUNIT" 2)		;DIMLUNIT Задает единицы для всех типов размеров, кроме угловых.
       (list "DIMLWD" -2)		;DIMLWD Задает вес размерных линий. Значения выбираются из стандартного списка.		
       (list "DIMLWE" -2)		;DIMLWE Задает вес выносных линий. Значения выбираются из стандартного списка.
       (list "DIMPOST" "")		;DIMPOST Задает префикс или суффикс текста (или и того, и другого) для размерных единиц. Чтобы задать размерный суффикс, обозначающий единицы измерения (миллиметры), следует присвоить DIMPOST значение "мм". Тогда, например, измеренное значение расстояния 19.2 единиц будет представлено на чертеже как "19.2 мм".
       (list "DIMRND" 0.0)		;DIMRND Служит для округления всех размерных расстояний в соответствии с указанным значением. Например, если задать значение 0.25, все измеренные расстояния будут округлены до ближайшего кратного 0.25. Если же DIMRND равна 1.0, все измеренные расстояния будут округлены до ближайшего целого. Следует учитывать, что количество цифр, воспринимаемых после десятичной точки, зависит от значения переменной DIMDEC. На угловые размеры DIMRND не действует.
       (list "DIMSAH" 0)		;DIMSAH Управление отображением блоков стрелок размерных линий.
       (list "DIMSCALE" 1.0)		;DIMSCALE Задает общий коэффициент масштабирования, применяемый для размерных переменных, задающих размеры, расстояния или смещения.
       (list "DIMSD1" 0)		;DIMSD1 Управляет подавлением первой размерной линии и стрелки.
       (list "DIMSD2" 0)		;DIMSD2 Управляет подавлением второй размерной линии и стрелки.
       (list "DIMSE1" 0)		;DIMSE1 Подавляет отображение первой выносной линии.
       (list "DIMSE2" 0)		;DIMSE2 Подавляет отображение второй выносной линии.
       (list "DIMSHO" 1)
       (list "DIMSOXD" 0)		;DIMSOXD Если для стрелок недостаточно места между выносными линиями, они подавляются.
;;;    (list "DIMSTYLE" "001_001")	;DIMSTYLE Сохраняется имя текущего размерного стиля. Имя этой системной переменной совпадает с названием команды. Для доступа к этой системной переменной служит команда УСТПЕРЕМ. Системная переменная DIMSTYLE доступна только для чтения; для изменения текущего размерного стиля используйте команду РЗМСТИЛЬ. 
       (list "DIMTAD" 1)		;DIMTAD Управляет положением размерного текста по вертикали относительно размерной линии.
       (list "DIMTDEC" 2)		;DIMTDEC Задает число знаков после запятой для значений допусков размеров в основных единицах. Эта системная переменная не оказывает никакого влияния, если переменная DIMTOL отключена. Значение по умолчанию для переменной DIMTOL является Откл.
       (list "DIMTFAC" 1.0)		;DIMTFAC Задает масштабный коэффициент для высоты текста дробных частей размеров и допусков относительно высоты размерного текста, заданной переменной DIMTXT. Например, если DIMTFAC = 1.0, дробные части размеров и допуски имеют ту же высоту, что и размерный текст. Если DIMTFAC = 0.7500, высота дробных частей размеров и допусков составляет три четверти высоты размерного текста. 
       (list "DIMTFILL" 0)		;DIMTFILL Управляет фоном размерного текста.
       (list "DIMTFILLCLR" 0)		;DIMTFILLCLR Задание цвета фона текста в размерах. Номера цветов отображаются в диалоговом окне "Выбор цвета". Для задания значения "ПОБЛОКУ" введите 0. Для задания значения "ПОСЛОЮ" введите 256.
       (list "DIMTIH" 0)		;DIMTIH Управляет расположением размерного текста для всех типов размеров, кроме ординатных, если текст вписывается между выносными линиями.
       (list "DIMTIX" 0)		;DIMTIX Отображает текст между выносными линиями.
       (list "DIMTM" 0.0)		;DIMTM Устанавливает наименьший (или нижний) предел допуска для размерного текста при включенной переменной DIMTOL или DIMLIM. Переменная DIMTM допускает значения с любым знаком. Если переменная DIMTOL включена, а значения переменных DIMTP и DIMTM равны, отображается значение допуска.
       (list "DIMTMOVE" 0)		;DIMTMOVE Устанавливает правила перемещения размерного текста.
       (list "DIMTOFL" 1)		;DIMTOFL Управляет построением размерной линии между выносными линиями, даже если текст размещается вне линий. Для радиусов и диаметров (при отключенной переменной DIMTIX) размерная линия проводится внутри круга или дуги, а текст, стрелки и выноска размещаются снаружи.
       (list "DIMTOH" 0)		;DIMTOH Управление расположением размерного текста за выносными линиями.
       (list "DIMTOL" 0)		;DIMTOL Добавление предельных отклонений в конец размерного текста. Включение переменной DIMTOL приводит к отключению переменной DIMLIM.
       (list "DIMTOLJ" 1)		;DIMTOLJ Задает выравнивание значений допусков относительно номинального размерного текста. Эта системная переменная не оказывает никакого влияния, если переменная DIMTOL отключена. Значение по умолчанию для переменной DIMTOL является Откл. 
       (list "DIMTP" 0.0)		;DIMTP Устанавливает максимальное (или верхнее) предельное отклонение для размерного текста при включенной переменной DIMTOL или DIMLIM. Переменная DIMTOL допускает значения с любым знаком. Если переменная DIMTOL включена, а значения переменных DIMTP и DIMTM равны, отображается значение допуска.
       (list "DIMTSZ" 0.0)		;DIMTSZ Указывает размер засечки, которая наносится вместо стрелки в линейных размерах, радиусах и диаметрах.
       (list "DIMTVP" 0.0)		;DIMTVP Задает вертикальное расположение размерного текста над или под размерной линией. Значение переменной DIMTVP используется, когда переменная DIMTAD отключена. Значение смещения текста по вертикали вычисляется как произведение высоты текста и DIMTVP. Присвоение переменной DIMTVP значения 1.0 эквивалентно включению переменной DIMTAD. Размерная линия разрывается в соответствии с текстом, только если абсолютная величина DIMTVP меньше 0.7.
       (list "DIMTXSTY" "t")		;DIMTXSTY Задает текстовый стиль для размера.
       (list "DIMTXT" 5.0)		;DIMTXT Задает высоту размерного текста, если в текстовом стиле не задана фиксированная высота.
       (list "DIMTZIN" 8)		;DIMTZIN Управляет подавлением нулей в значениях допуска. Значения от 0 до 3 относятся только к размерам, выраженным в футах и дюймах.
       (list "DIMUNIT" 2)
       (list "DIMUPT" 0)		;DIMUPT Управляет параметрами при пользовательском расположении текста.
       (list "DIMZIN" 8)		;DIMZIN Управляет подавлением нулей в значениях, заданных в основных единицах измерения. Значения от 0 до 3 относятся только к размерам, выраженным в футах и дюймах.
     )
  )
  (stl)
  (mapcar
    (function
      (lambda (el)
	(setvar (car el) (cadr el))
      )
    )
    dim_var_lst
  )
)

(defun create_dim_styles (/ dstyle_size)
  (setq
    dstyle_size
     (list
       (list "0100_1" (/ 1.0 100.0))
       (list "0050_1" (/ 1.0 50.0))
       (list "0040_1" (/ 1.0 40.0))
       (list "0020_1" (/ 1.0 20.0))
       (list "0010_1" (/ 1.0 10.0))
       (list "0005_1" (/ 1.0 5.0))
       (list "0004_1" (/ 1.0 4.0))
       (list "0002i5_1" (/ 1.0 2.5))
       (list "0002_1" (/ 1.0 2.0))

       (list "0001_1"   (* 1.0 1.0))

       (list "1_0002"   (* 1.0 2.0))
       (list "1_0002i5" (* 1.0 2.5))
       (list "1_0004"   (* 1.0 4.0))
       (list "1_0005"   (* 1.0 5.0))
       (list "1_0010"   (* 1.0 10.0))
       (list "1_0015"   (* 1.0 15.0))
       (list "1_0020"   (* 1.0 20.0))
       (list "1_0025"   (* 1.0 25.0))
       (list "1_0040"   (* 1.0 40.0))
       (list "1_0050"   (* 1.0 50.0))
       (list "1_0075"   (* 1.0 75.0))
       (list "1_0100"   (* 1.0 100.0))
       (list "1_0200"   (* 1.0 200.0))
       (list "1_0400"   (* 1.0 400.0))
       (list "1_0500"   (* 1.0 500.0))
       (list "1_0800"   (* 1.0 800.0))
       (list "1_1000"  (* 1.0 1000.0))
     )
  )
  (mapcar
    (function
      (lambda (el)
	(load_dim_vars)
	(setvar "DIMSCALE" (cadr el))
	(command "_DIMSTYLE" "_save" (car el))
	(if (= 1 (getvar "cmdactive"))
	  (command "_Y")
	)
      )
    )
    dstyle_size
  )
)

(defun c:MNASAddDimStyle()
  (create_dim_styles)
  (command "_-DIMSTYLE" "_restore" "0001_1")
  (princ)
)

;|«Visual LISP© Format Options»
(105 2 15 2 nil "end of" 90 9 0 0 0 T T nil T)
;*** НЕ добавляйте текст под комментариями! ***|;
