(setvar "DIMADEC" 0)			; "DIMADEC"           0
(setvar "DIMALT" 0)			; "DIMALT"            Откл
(setvar "DIMALTD" 3)			; "DIMALTD"           3
(setvar "DIMALTF" (/ 10. 254.))		; "DIMALTF"           0.0394
(setvar "DIMALTRND" 0.0)		; "DIMALTRND"         0.0000
(setvar "DIMALTTD" 3)			; "DIMALTTD"          4
(setvar "DIMALTTZ" 0)			; "DIMALTTZ"          0
(setvar "DIMALTU" 2)			; "DIMALTU"           2
(setvar "DIMALTZ" 0)			; "DIMALTZ"           0
(setvar "DIMAPOST" "")			; "DIMAPOST"          ""
(setvar "DIMARCSYM" 0)			; "DIMARCSYM"         0
(setvar "DIMASO" 1)			; "DIMASO"            Вкл
(setvar "DIMASSOC" 2)			; "DIMASSOC"          2
(setvar "DIMASZ" 3.5)			; "DIMASZ"            3.5000
(setvar "DIMATFIT" 3)			; "DIMATFIT"          2
(setvar "DIMAUNIT" 0)			; "DIMAUNIT"          1
(setvar "DIMAZIN" 0)			; "DIMAZIN"           2
(setvar "DIMBLK" "")			; "DIMBLK"            ""
(setvar "DIMBLK1" "")			; "DIMBLK1"           ""
(setvar "DIMBLK2" "")			; "DIMBLK2"           ""
(setvar "DIMCEN" 2.5)			; "DIMCEN"            2.5000
(setvar "DIMCLRD" 0)			; "DIMCLRD"           0
(setvar "DIMCLRE" 0)			; "DIMCLRE"           0
(setvar "DIMCLRT" 0)			; "DIMCLRT"           0
(setvar "DIMDEC" 2)			; "DIMDEC"            2
(setvar "DIMDLE" 0.0000)		; "DIMDLE"            0.0000
(setvar "DIMDLI" 3.7500)		; "DIMDLI"            10.0000
(setvar "DIMDSEP" ",")			; "DIMDSEP"           ","
(setvar "DIMEXE" 1.5000)		; "DIMEXE"            1.5000
(setvar "DIMEXO" 0.0000)		; "DIMEXO"            0.0000
(setvar "DIMFIT" 3)			; "DIMFIT"            2
(setvar "DIMFRAC" 0)			; "DIMFRAC"           0
(setvar "DIMFXL" 1.0000)		; "DIMFXL"            1.0000
(setvar "DIMFXLON" 0)			; "DIMFXLON"          Откл
(setvar "DIMGAP" 1.5000)		; "DIMGAP"            1.5000
(setvar "DIMJOGANG" 0.785398)		; "DIMJOGANG"         45
(setvar "DIMJUST" 0)			; "DIMJUST"           0
(setvar "DIMLDRBLK" "")			; "DIMLDRBLK"         ""
(setvar "DIMLFAC" 1.0000)		; "DIMLFAC"           1.0000
(setvar "DIMLIM" 0)			; "DIMLIM"            Откл
;;;(setvar "DIMLTEX1" "")			; "DIMLTEX1"          ""
;;;(setvar "DIMLTEX2" "")			; "DIMLTEX2"          ""
;;;(setvar "DIMLTYPE" "")			; "DIMLTYPE"          ""
(setvar "DIMLUNIT" 2)			; "DIMLUNIT"          2
(setvar "DIMLWD" -2)			; "DIMLWD"            -2
(setvar "DIMLWE" -2)			; "DIMLWE"            -2
(setvar "DIMPOST" "")			; "DIMPOST"           ""
(setvar "DIMRND" 0.0000)		; "DIMRND"            0.0000
(setvar "DIMSAH" 0)			; "DIMSAH"            Откл
(setvar "DIMSCALE" 1.00)		; "DIMSCALE"          1.0000
(setvar "DIMSD1" 0)			; "DIMSD1"            Откл
(setvar "DIMSD2" 0)			; "DIMSD2"            Откл
(setvar "DIMSE1" 0)			; "DIMSE1"            Откл
(setvar "DIMSE2" 0)			; "DIMSE2"            Откл
(setvar "DIMSHO" 1)			; "DIMSHO"            Вкл
(setvar "DIMSOXD" 0)			; "DIMSOXD"           Откл
;;;(setvar "DIMSTYLE" "001_001")		; "DIMSTYLE"          "001_001" (только чтение)
(setvar "DIMTAD" 3)			; "DIMTAD"            1
(setvar "DIMTDEC" 2)			; "DIMTDEC"           2
(setvar "DIMTFAC" 1.0)			; "DIMTFAC"           1.0000
(setvar "DIMTFILL" 0)			; "DIMTFILL"          0
(setvar "DIMTFILLCLR" 0)		; "DIMTFILLCLR"       0
(setvar "DIMTIH" 0)			; "DIMTIH"            Откл
(setvar "DIMTIX" 0)			; "DIMTIX"            Откл
(setvar "DIMTM" 0.0000)			; "DIMTM"             0.0000
(setvar "DIMTMOVE" 0)			; "DIMTMOVE"          0
(setvar "DIMTOFL" 1)			; "DIMTOFL"           Вкл
(setvar "DIMTOH" 1)			; "DIMTOH"            Откл
(setvar "DIMTOL" 0)			; "DIMTOL"            Откл
(setvar "DIMTOLJ" 0)			; "DIMTOLJ"           1
(setvar "DIMTP" 0.0000)			; "DIMTP"             0.0000
(setvar "DIMTSZ" 0.0000)		; "DIMTSZ"            0.0000
(setvar "DIMTVP" 0.0000)		; "DIMTVP"            0.0000
(setvar "DIMTXSTY" "Standard")		; "DIMTXSTY"          "t"
(setvar "DIMTXT" 3.5000)		; "DIMTXT"            3.5000
(setvar "DIMTZIN" 8)			; "DIMTZIN"           8
(setvar "DIMUNIT" 2)			; "DIMUNIT"           2
(setvar "DIMUPT" 0)			; "DIMUPT"            Откл
(setvar "DIMZIN" 8)			; "DIMZIN"            8

(setq
  dim_var_lst
   (LIST
     "DIMADEC"	   "DIMALT"	 "DIMALTD"     "DIMALTF"
     "DIMALTRND"   "DIMALTTD"	 "DIMALTTZ"    "DIMALTU"
     "DIMALTZ"	   "DIMAPOST"	 "DIMARCSYM"   "DIMASO"
     "DIMASSOC"	   "DIMASZ"	 "DIMATFIT"    "DIMAUNIT"
     "DIMAZIN"	   "DIMBLK"	 "DIMBLK1"     "DIMBLK2"
     "DIMCEN"	   "DIMCLRD"	 "DIMCLRE"     "DIMCLRT"
     "DIMDEC"	   "DIMDLE"	 "DIMDLI"      "DIMDSEP"
     "DIMEXE"	   "DIMEXO"	 "DIMFIT"      "DIMFRAC"
     "DIMFXL"	   "DIMFXLON"	 "DIMGAP"      "DIMJOGANG"
     "DIMJUST"	   "DIMLDRBLK"	 "DIMLFAC"     "DIMLIM"
     "DIMLTEX1"	   "DIMLTEX2"	 "DIMLTYPE"    "DIMLUNIT"
     "DIMLWD"	   "DIMLWE"	 "DIMPOST"     "DIMRND"
     "DIMSAH"	   "DIMSCALE"	 "DIMSD1"      "DIMSD2"
     "DIMSE1"	   "DIMSE2"	 "DIMSHO"      "DIMSOXD"
     "DIMSTYLE"	   "DIMTAD"	 "DIMTDEC"     "DIMTFAC"
     "DIMTFILL"	   "DIMTFILLCLR" "DIMTIH"      "DIMTIX"
     "DIMTM"	   "DIMTMOVE"	 "DIMTOFL"     "DIMTOH"
     "DIMTOL"	   "DIMTOLJ"	 "DIMTP"       "DIMTSZ"
     "DIMTVP"	   "DIMTXSTY"	 "DIMTXT"      "DIMTZIN"
     "DIMUNIT"	   "DIMUPT"	 "DIMZIN"
    )
)

(setq
  dim_var_val
   (mapcar
     (function (lambda (el) (getvar el)))
     dim_var_lst
   )
)

(mapcar 'list dim_var_lst dim_var_val)
