(setq *dim-style-command-list*
       '("MNASAddDimStyle" "dim-toh" "dim-rad-hor" "dim-rad-rad" "DIM-SD_SE" "MNASsetDimjust" "MNASsetDimtofl"
         "MNASsetDimtad" "MNASsetDimtmove" "MNASsetDimsd1" "MNASsetDimsd2" "MNASsetDimatfit" "MNASsetDimtoh"
         "dim_0001_1"))
;;;; (opech_cmds-str *dim-style-command-list*)

(defun c:ÜÒÔÛÔââÂøüÛåíäó() (c:MNASAddDimStyle))
(defun c:âøü-åùð() (c:dim-toh))
(defun c:âøü-êôâ-ðùê() (c:dim-rad-hor))
(defun c:âøü-êôâ-êôâ() (c:dim-rad-rad))
(defun c:ÂØÜ-ÛÂ_ÛÓ() (c:DIM-SD_SE))
(defun c:ÜÒÔÛûóåÂøüîãûå() (c:MNASsetDimjust))
(defun c:ÜÒÔÛûóåÂøüåùàä() (c:MNASsetDimtofl))
(defun c:ÜÒÔÛûóåÂøüåôâ() (c:MNASsetDimtad))
(defun c:ÜÒÔÛûóåÂøüåüùìó() (c:MNASsetDimtmove))
(defun c:ÜÒÔÛûóåÂøüûâ1() (c:MNASsetDimsd1))
(defun c:ÜÒÔÛûóåÂøüûâ2() (c:MNASsetDimsd2))
(defun c:ÜÒÔÛûóåÂøüôåàøå() (c:MNASsetDimatfit))
(defun c:ÜÒÔÛûóåÂøüåùð() (c:MNASsetDimtoh))
(defun c:âøü_0001_1() (c:dim_0001_1))

(princ "Loaded project dim_style.\n")
