(setq *dims-command-list*
       '("ins_blk" "bas" "poz" "up" "bot" "d_up" "cut" "look" "obj_data" "dwg_put" "dwg_get" "welding" "index_ru"
         "index_en" "index" "lea"))
;;;; (opech_cmds-str *dims-command-list*)

(defun c:ЬРШ_ХДК() (c:ins_blk))
(defun c:ХТШ() (c:bas))
(defun c:ГЫЪ() (c:poz))
(defun c:ЦГ() (c:up))
(defun c:ХЫЕ() (c:bot))
(defun c:Б_ЦГ() (c:d_up))
(defun c:ЯЦЕ() (c:cut))
(defun c:ДЫЫК() (c:look))
(defun c:ЫХН_БТЕТ() (c:obj_data))
(defun c:БЖО_ГЦЕ() (c:dwg_put))
(defun c:БЖО_ОСЕ() (c:dwg_get))
(defun c:ЖСДБЬРО() (c:welding))
(defun c:ЬРБСВ_ЙЦ() (c:index_ru))
(defun c:ЬРБСВ_СР() (c:index_en))
(defun c:ЬРБСВ() (c:index))
(defun c:ДСТ() (c:lea))

(princ "Loaded project dims.\n")
