(defun c:lea  (/ k str i key_list key_str)
  (setq key_list (list "Arrow" "dotSmall" "weldTop" "weldBot"))
  (setq key_str "")
  (mapcar (function (lambda (el) (setq key_str (strcat key_str "/" el)))) key_list)
  (prompt "Выберите объекты типа LEADER для изменения стрелки:")
  (setq ss (ssget '((0 . "LEADER"))))
  (initget (key_words->prompt_list key_list " "))
  (setq k (getkword (strcat "Arrow type [" (key_words->prompt_list key_list "/") "]:")))
  (cond	((= (nth 0 key_list) k) (setq str ""))
	((= (nth 1 key_list) k) (setq str "DotSmall"))
	((= (nth 2 key_list) k)
	 (setq str "weld_arrow_top")
	 (if (not (TBLSEARCH "BLOCK" "weld_arrow_top"))
	   (progn (command "_-INSERT" "weld_arrow_top" "*0,0,0" "1" "" "")
		  (command "_erase" "_last" ""))))
	((= (nth 3 key_list) k)
	 (setq str "weld_arrow_bot")
	 (if (not (TBLSEARCH "BLOCK" "weld_arrow_bot"))
	   (progn (command "_-INSERT" "weld_arrow_bot" "*0,0,0" "1" "" "")
		  (command "_erase" "_last" "")))))
  (setq i (sslength ss))
  (while (<= 0 (setq i (1- i)))
    (vlax-put-property (vlax-ename->vla-object (ssname ss i)) 'ArrowheadBlock str)))

(defun key_words->prompt_list  (key_word dev_str / str)
  (setq	str	 (car key_word)
	key_word (cdr key_word))
  (while (null (not key_word))
    (setq str	   (strcat str dev_str (car key_word))
	  key_word (cdr key_word)))
  str)
