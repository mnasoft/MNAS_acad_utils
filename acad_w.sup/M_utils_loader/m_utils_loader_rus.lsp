(setq *m_utils_loader-command-list* '("mnas-cad-utils-path" "MNASoft-registry-uninstall" "MNASoft-registry-install"))
;;;; (opech_cmds-str *m_utils_loader-command-list*)

(defun c:üòôû-ñôâ-ãåøäû-çôåð() (c:mnas-cad-utils-path))
(defun c:ÜÒÔÛùàå-êóïøûåêí-ãòøòûåôää() (c:MNASoft-registry-uninstall))
(defun c:ÜÒÔÛùàå-êóïøûåêí-øòûåôää() (c:MNASoft-registry-install))

(princ "Loaded project m_utils_loader.\n")
