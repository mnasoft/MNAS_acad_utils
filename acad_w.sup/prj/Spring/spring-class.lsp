(defun get (key) (setq tmp (atof (get_tile key))) (set_tile key (rtos tmp)) tmp)

(defun put (key val) (atof (set_tile key (rtos val))))

(defun d () (put "D" (- (get "D1") (get "d"))))

(defun d1 () (put "D1" (+ (get "d") (get "D"))))

(defun _i () (put "i" (/ (get "D") (get "d"))))

(defun _i1 () (put "i1" (/ (get "L0") (get "D"))))

(defun l0 () (put "L0" (+ (* (get "n") (get "t")) (* 1.5 (get "d")))))

(defun l1 () (put "L1" (- (get "L0") (get "S1"))))

(defun l2 () (put "L2" (- (get "L0") (get "S2"))))

(defun l3 () (put "L3" (- (get "L0") (get "S3"))))

(defun l4 () (put "L4" (* (+ (get "n") 1.5) (get "d"))))

(defun s1 () (put "S1" (- (get "L0") (get "L1"))))

(defun s2 () (put "S2" (- (get "L0") (get "L2"))))

(defun s3 () (put "S3" (- (get "L0") (get "L3"))))

(defun l  (/ d _t)
  (setq d  (get "D")
        _t (get "t"))
  (put "L" (* (get "n1") (sqrt (+ (* pi pi d d) (* _t _t))))))

(defun _n () (put "n" (- (get "n1") 2.0)))

(defun _n1 () (put "n1" (+ (get "n") 2.0)))

(defun _t () (put "t" (/ (- (get "L0") (* 1.5 (get "d"))) (get "n"))))

(defun _h () (put "h" (- (get "S2") (get "S1"))))

(defun k1 (/ i) (setq i (_i)) (put "K1" (+ (/ (- (* 4.0 i) 1.0) (- (* 4.0 i) 4.0)) (/ 0.615 i))))

(defun k2 (/ i) (setq i (_i)) (put "K2" (+ 1.0 (/ 1.0 2.0 i) (/ -1.0 2.0 i i))))

(defun f1  (/ d_big d_sm)
  (setq d_sm  (get "d")
        d_big (get "D"))
  (put "F1" (/ (* (get "G") d_sm d_sm d_sm d_sm (get "S1")) 8.0 d_big d_big d_big (get "n") (k2))))

(defun f2  (/ d_big d_sm)
  (setq d_sm  (get "d")
        d_big (get "D"))
  (put "F2" (/ (* (get "G") d_sm d_sm d_sm d_sm (get "S2")) 8.0 d_big d_big d_big (get "n") (k2))))

(defun f3  (/ d_big d_sm)
  (setq d_sm  (get "d")
        d_big (get "D"))
  (put "F3" (/ (* (get "G") d_sm d_sm d_sm d_sm (get "S3")) 8.0 d_big d_big d_big (get "n") (k2))))

(defun _tau1  ()
  (setq d_sm (get "d"))
  (put "tau1" (/ (* 2.55 (get "F1") (get "D") (get "K1")) (* d_sm d_sm d_sm))))

(defun _tau2  ()
  (setq d_sm (get "d"))
  (put "tau2" (/ (* 2.55 (get "F2") (get "D") (get "K1")) (* d_sm d_sm d_sm))))
(defun _tau3  ()
  (setq d_sm (get "d"))
  (put "tau3" (/ (* 2.55 (get "F3") (get "D") (get "K1")) (* d_sm d_sm d_sm))))

(defun c () (put "C" (/ (- (get "F2") (get "F1")) (get "h"))))

(defun m  (/ _d _n1)
  (setq _d  (get "d")
        _n1 (get "n1"))
  (put "m" (* 8.0e-6 pi _d _d 0.25 (get "L") (/ (- _n1 0.5) _n1))))

(defun err () (set_tile "error" (strcat (cadr (assoc $key setup_msg)) " = " $value)))


(defun action_d  ()
  (err)
  (_t)
  (l4)
  (d1)
  (d)
  (_i1)
  (l)
  (_i)
  (k2)
  (f1)
  (f2)
  (f3)
  (k1)
  (_tau1)
  (_tau2)
  (_tau3)
  (c)
  (m)
  (stp_lst))

(defun actiond  ()
  (err)
  (d1)
  (_i1)
  (l)
  (_i)
  (k2)
  (f1)
  (f2)
  (f3)
  (k1)
  (_tau1)
  (_tau2)
  (_tau3)
  (c)
  (m)
  (stp_lst))

(defun actiond1  ()
  (err)
  (d)
  (_i1)
  (l)
  (_i)
  (k2)
  (f1)
  (f2)
  (f3)
  (k1)
  (_tau1)
  (_tau2)
  (_tau3)
  (c)
  (m)
  (stp_lst))

(defun action_n1  ()
  (err)
  (_n)
  (l4)
  (l0)
  (_t)
  (_i1)
  (l)
  (l1)
  (l2)
  (l3)
  (s1)
  (s2)
  (s3)
  (_h)
  (f1)
  (f2)
  (f3)
  (_tau1)
  (_tau2)
  (_tau3)
  (c)
  (m)
  (stp_lst))

(defun action_n  ()
  (err)
  (_n1)
  (l4)
  (l0)
  (_t)
  (_i1)
  (l)
  (l1)
  (l2)
  (l3)
  (s1)
  (s2)
  (s3)
  (_h)
  (f1)
  (f2)
  (f3)
  (_tau1)
  (_tau2)
  (_tau3)
  (c)
  (m)
  (stp_lst))

(defun action_t  ()
  (err)
  (l)
  (l0)
  (_t)
  (_i1)
  (l)
  (l1)
  (l2)
  (l3)
  (s1)
  (s2)
  (s3)
  (_h)
  (f1)
  (f2)
  (f3)
  (_tau1)
  (_tau2)
  (_tau3)
  (c)
  (m)
  (stp_lst))

(defun actionl0  ()
  (err)
  (_t)
  (_i1)
  (l)
  (l1)
  (l2)
  (l3)
  (s1)
  (s2)
  (s3)
  (_h)
  (f1)
  (f2)
  (f3)
  (_tau1)
  (_tau2)
  (_tau3)
  (c)
  (m)
  (stp_lst))

(defun actions1 () (err) (l1) (_h) (f1) (_tau1) (c) (m) (stp_lst))

(defun actionl1 () (err) (s1) (_h) (f1) (_tau1) (c) (m) (stp_lst))


(defun actions2 () (err) (l2) (_h) (f2) (_tau2) (c) (m) (stp_lst))

(defun actionl2 () (err) (s2) (_h) (f2) (_tau2) (c) (m) (stp_lst))

(defun actions3 () (err) (l3) (f3) (_tau3) (stp_lst))

(defun actionl3 () (err) (s3) (f3) (_tau3) (stp_lst))

(defun actiong () (err) (f1) (f2) (f3) (_tau1) (_tau2) (_tau3) (c) (m) (stp_lst))
