;;;Gv/Gg	dT	T2	NOx	CO
;;;
;;;	275
(setq gr_1
       '(
	 (0.00 341. 304. 33. 80.)
	 (0.32 338. 311. 25. 95.)
	 (0.61 353. 305. 18. 140.)
	 (0.89 355. 301. 14. 238.)
	 (1.18 352. 300. 16. 258.)
	 (1.65 353. 302. 18. 219.)
	 (2.02 353. 302. 16. 329.)
	 (2.26 354. 302. 12. 638.)
	 (0.00 345. 302. 31. 79.)
	 (0.00 465. 371. 66. 44.)
	 (0.31 458. 383. 53. 43.)
	 (0.57 455. 385. 45. 45.)
	 (1.10 455. 384. 43. 58.)
	 (1.81 454. 379. 31. 208.)
	 (2.13 374. 372. 21. 268.)
;;;	276
	 (0.00 294. 131. 12. 333.)
	 (0.00 299. 190. 18. 198.)
	 (0.00 268. 243. 18. 148.)
	 (0.00 327. 281. 29. 85.)
	 (0.00 352. 302. 37. 66.)
	 (0.41 343. 307. 25. 88.)
	 (0.70 350. 306. 21. 143.)
	 (1.13 349. 309. 21. 210.)
	 (1.60 351. 308. 23. 166.)
	 (2.18 355. 303. 16. 500.)
	 (0.00 422. 342. 58. 46.)
	 (0.34 416. 344. 39. 50.)
	 (0.55 419. 347. 35. 60.)
	 (0.924 425. 349. 37. 70.)
	 (1.30 422. 350. 35. 86.)
	 (1.90 416. 352. 27. 229.)
	 (0.00 471. 377. 70. 31.)
	 (0.36 477. 375. 53. 36.)
	 (0.50 479. 375. 49. 36.)
	 (0.82 475. 376. 45. 43.)
	 (1.12 471. 376. 45. 53.)
	 (1.64 471. 378. 33. 130.)
	)
)
;;;	278
(setq gr_2 '(
	     (0.00 310. 161. 6. 1861.)
	     (0.00 335. 196. 12. 2670.)
	     (0.00 444. 346. 49. 463.)
	     (0.4 447. 345. 35. 650.)
	     (0.73 443. 346. 29. 820.)
	     (1.25 453. 348. 21. 2670.)
	     (1.69 447. 349. 18. 2375.)
	     (2.08 456. 349. 14. 3000.)
	     (2.63 463. 344. 18 4500.)
;;;	279
	     (0.00 269. 243. 12. 1213.)
	     (0.00 349. 284. 29. 813.)
	     (0.00 368. 300. 35. 684.)
	     (0.42 367. 303. 25. 981.)
	     (0.73 366. 304. 21. 920.)
	     (0.76 377. 306. 18. 1038.)
	     (1.37 364. 311. 14. 1500.)
	     (1.8 372. 306. 14. 2250.)
	     (2.14 373. 303. 21. 3125.)
	     (2.52 381. 306. 21. 4063.)
	     (0.00 476. 379. 74. 228.)
	     (0.43 474. 379. 47. 485.)
	     (0.83 479. 378. 37. 839.)
	     (1.27 472. 379. 25. 1500.)
	     (1.67 486. 379. 23. 1950.0)
	     (2.06 481. 382. 16. 3125.)
	     (2.54 477. 383. 14. 4750.)
;;;	280
	     (0.00 310. 161. 6. 1861.)
	     (0.00 335. 196. 12. 2670.)
	     (0.00 444. 346. 49. 463.)
	     (0.4 447. 345. 35. 650.)
	     (0.73 443. 346. 29. 820.)
	     (1.25 453. 348. 21. 2670.)
	     (1.69 447. 349. 18. 2375.)
	     (2.08 456. 349. 14. 3000.)
	     (2.63 463. 344. 18. 4500.)
	    )
)

(setq gr_3
       '(
;;;	283
	 (0.00 368. 316. 45. 813.)
	 (0.28 362. 311. 41. 881.)
	 (0.47 376. 312. 33. 954.)
	 (0.85 373. 312. 16. 1875.)

;;;	284
	 (0.00 365. 308. 43. 863.)
	 (0.26 367. 307. 27. 850.)
	 (0.43 363. 309. 14. 2500.)
	 (0.67 372. 309. 12. 2125.)

;;;	285
	 (0.00 364. 295. 37. 1000.)
	 (0.2942478 360. 298. 31. 968.)
	 (0.4617068 356. 302. 27. 975.)
	 (0.9143969 360. 304. 14. 1875.)
	 (1.259259 355. 306. 10. 1375.)
	 (0.00 431. 344. 58. 625.)
	 (0.1946565 425. 350. 49. 613.)
	 (0.4725379 420. 349. 37. 675.)
	 (0.8822464 418. 349. 23. 1313.)
	 (1.05614 432. 349. 18. 963.)
	 (1.273043 425. 348. 16. 869.)
	 (0.00 467. 373. 80. 313.)
	 (0.2292769 459. 378. 66. 358.)
	 (0.4205934 460. 372. 51. 408.)
	 (0.7828283 460. 372. 31. 875.)
	 (0.9540983 460. 375. 29. 600.)
	 (1.137097 470. 375. 23. 523.)
	)
)

(setq gr_4 '(
;;;	286
	     (0.00 352. 306. 31. 71.)
	     (0.3878117 340. 310. 18. 113.)
	     (0.7196766 347. 305. 12. 261.)
	     (0.9928572 365. 301. 8. 730.)
	     (1.10124 394. 304. 8. 1168.)
	     (1.137856 358. 307. 6. 1254.)
	     (0.00 415. 340. 45. 50.)
	     (0.2946636 424. 344. 31. 56.)
	     (0.5858123 417. 346. 23. 95.)
	     (0.9429825 418. 346. 16. 281.)
	     (1.191919 421. 346. 10. 975.)
	     (0.00 469. 370. 62. 36.)
	     (0.2377919 464. 379. 45. 36.)
	     (0.5073069 459. 382. 35. 45.)
	     (0.8770161 461. 380. 23. 129.)
	     (1.124764 470. 374. 14. 499.)
	    )
)

(setq gr_5 '(
;;;	287
	     (0.00 356. 303. 31. 75.)
	     (0.00 423. 345. 47. 50.)
	     (0.5563219 414. 344. 23. 99.)
	     (1.013072 407. 344. 12. 438.)
	     (1.153374 412. 342. 10. 969.)
	     (0.3186046 413. 341. 31. 64.)
	     (0.3050802 356. 300. 21. 105.)
	     (0.6408268 357. 299. 14. 223.)
	     (1. 358. 298. 8. 770.)
	     (1.073276 361. 301. 8. 1175.)
	     (0.00 462. 375. 64. 35.)
	     (0.2484848 470. 371. 45. 41.)
	     (0.4585859 463. 372. 37. 50.)
	     (0.8252427 464. 373. 23. 134.)
	     (1.005714 462. 374. 18. 334.)
	    )
)


(defun nox-g_g-t02
		   (el)
  (list	(nth 0 el)
	(nth 1 el)
	(nth 3 el)
  )
)

(defun nox_pnts	(gr)
  (mapcar
    (function nox-g_g-t02)
    gr
  )
)

(defun co-g_g-t02
		  (el)
  (list	(nth 0 el)
	(nth 1 el)
	(nth 4 el)
  )
)

(defun co_pnts (gr)
  (mapcar
    (function nox-g_g-t02)
    gr
  )
)

;;;;;;("culc_co_nox" "not defined" "not defined")
(defun c:culc_co_nox (/ arg_list fuc_type)
  (setq arg_list '(X1 X2 YY))
  (setq fuc_type '((X1 X1) (X2 X2) (X1 X2) (X1) (X2) (1.0) (YY)))
  (osr_func arg_list fuc_type (nox_pnts gr_1) 'nox_1)
  (osr_func arg_list fuc_type (nox_pnts gr_2) 'nox_2)
  (osr_func arg_list fuc_type (nox_pnts gr_3) 'nox_3)
  (osr_func arg_list fuc_type (nox_pnts gr_4) 'nox_4)
  (osr_func arg_list fuc_type (nox_pnts gr_5) 'nox_5)

  (osr_func arg_list fuc_type (co_pnts gr_1) 'co_1)
  (osr_func arg_list fuc_type (co_pnts gr_2) 'co_2)
  (osr_func arg_list fuc_type (co_pnts gr_3) 'co_3)
  (osr_func arg_list fuc_type (co_pnts gr_4) 'co_4)
  (osr_func arg_list fuc_type (co_pnts gr_5) 'co_5)
  (mapcar 'print (list nox_1 nox_2 nox_3 nox_4 nox_5 co_1 co_2 co_3 co_4 co_5))
  (princ)
)

;;;;;;("sech" "not defined" "not defined")
(defun c:sech (/ dt)
  (setq func (eval (read (getstring "Введите имя функции:"))))
  (setq dt (getreal "Введите подогрев, С:"))
  (setq
    g_g-min (getreal "Отношение расхода воды к расходу топлива _min:")
  )
  (setq
    g_g-max (getreal "Отношение расхода воды к расходу топлива _max:")
  )

  (setq gg_lst (ndiv_min_max g_g-min g_g-max 100))
;;;  (mapcar
;;;    (function
;;;      (lambda (el))
;;;
;;;    )
;;;  )


)

;;;Делит интервал на заданное количество частей
;;;_$ (NDIV_MIN_MAX 0. 10. 5)
;;;(0.0 2.0 4.0 6.0 8.0 10.0)
(defun ndiv_min_max (g-from g-to n / val g_lst i)
  (setq
    i n
  )
  (while (>= i 0)
    (setq val	(+ g-from (/ (* i (- g-to g-from)) n))
	  g_lst	(cons val g_lst)
    )
    (setq i (1- i))
  )
  g_lst
)
;|«Visual LISP© Format Options»
(180 2 40 2 nil "end of " 100 9 0 0 0 T T nil T)
;*** DO NOT add text below the comment! ***|;
