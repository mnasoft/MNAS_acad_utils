;;;;;;("read_exel" "Чтение их Exel." "Обмен")
(defun c:read_exel (/ xls_tbl_pathname						; Путь к открываемой таблице
		    sheet_no							; Номер считываемой из Exel станицы
		    cell_lt							; Левая верхняя ячейка
		    cell_rb							; Правая нижняя ячейка
)
  (setq	xls_tbl_pathname
	 (getfiled "Заголовок" "" "xls" 0)
  )
  (setq sheet_no (getint "Введите номер страницы Exel:"))
  (setq	cell_lt	(getstring "Левая верхняя ячейка<A1>:")
	cell_lt
		(cond
		  ((= "" cell_lt)
		   "A1"
		  )
		  (cell_lt)
		)
  )

  (setq	cell_rb	(getstring "Правую нижнюю ячейку из диапазона ячеек:")
	cell_rb
		(cond
		  ((= "" cell_rb)
		   "IV65536"
		  )
		  (cell_rb)
		)
  )
  (read_exel xls_tbl_pathname sheet_no cell_lt cell_rb)
)
