(defun str_ru_eng ()
  '(("А" "A")
    ("Б" "B")
    ("В" "V")
    ("Г" "G")
    ("Д" "D")
    ("Е" "JE")
    ("Ё" "JO")
    ("Ж" "G")
    ("З" "Z")
    ("И" "I")
    ("Й" "J")
    ("К" "K")
    ("Л" "L")
    ("М" "M")
    ("Н" "N")
    ("О" "O")
    ("П" "P")
    ("Р" "R")
    ("С" "S")
    ("Т" "T")
    ("У" "U")
    ("Ф" "F")
    ("Х" "H")
    ("Ц" "TC")
    ("Ч" "CH")
    ("Х" "H")
    ("Ш" "SH")
    ("Щ" "SCH")
    ("Ь" "")
    ("Ы" "Y")
    ("Ъ" "")
    ("Э" "E")
    ("Ю" "JU")
    ("Я" "JA")

    ("а" "a")
    ("б" "b")
    ("в" "v")
    ("г" "g")
    ("д" "d")
    ("е" "je")
    ("ё" "jo")
    ("ж" "g")
    ("з" "z")
    ("и" "i")
    ("й" "j")
    ("к" "k")
    ("л" "l")
    ("м" "m")
    ("н" "n")
    ("о" "o")
    ("п" "p")
    ("р" "r")
    ("с" "s")
    ("т" "t")
    ("у" "u")
    ("ф" "f")
    ("х" "h")
    ("ц" "tc")
    ("ч" "ch")
    ("х" "h")
    ("ш" "sh")
    ("щ" "sch")
    ("ь" "")
    ("ы" "y")
    ("ъ" "")
    ("э" "e")
    ("ю" "ju")
    ("я" "ja")

    ("і" "i")
    ("І" "I")
    ("ё" "jo")
    ("Ё" "JO")
    ("є" "je")
    ("Є" "JE")
   )
)

;;;Производит изменение руссских и украинских символов на английские.
;;;(rename_ru_eng "Єто Это есть")
;;;(rename_ru_eng "абвгдеёжзийклмнопрстуфхцчшщъыьэюя")
;;;(RENAME_RU_ENG "АБВГДЕЁЖЗИЙКЛМНОПРСТУФХЦЧШЩЪЫЬЭЮЯ")
(defun rename_ru_eng (str / str_rez)
  (setq	str_lst	(VL-STRING->LIST str)
	str_rez	""
  )
  (mapcar
    (function
      (lambda (el / letter sym) 
	(setq sym    (chr el)
	      letter (assoc sym (str_ru_eng))
	)
	(cond
	  (letter
	   (setq str_rez (strcat str_rez (cadr letter)))
	  )
	  ((null letter)
	   (setq str_rez (strcat str_rez sym))
	  )
	)
	t
      )
    )
    str_lst
  )
  str_rez
)
