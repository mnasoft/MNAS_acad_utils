(setq *smesitel_vla-command-list* '("clear:sm" "dr:sech" "prep:sm" "dr:sm" "sm:help" "vla-obj-dump" "vla-obj"))
;;;; (opech_cmds-str *smesitel_vla-command-list*)

(defun c:сдуфкЖыь() (c:clear:sm))
(defun c:вкЖыуср() (c:dr:sech))
(defun c:зкузЖыь() (c:prep:sm))
(defun c:вкЖыь() (c:dr:sm))
(defun c:ыьЖрудз() (c:sm:help))
(defun c:мдф-щио-вгьз() (c:vla-obj-dump))
(defun c:мдф-щио() (c:vla-obj))

(princ "Loaded project smesitel_vla.\n")
