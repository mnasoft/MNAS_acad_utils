(setq *edit-command-list* '("mr" "mcp" "off" "ofd" "cr"))
;;;; (opech_cmds-str *edit-command-list*)

(defun c:üê() (c:mr))
(defun c:üñç() (c:mcp))
(defun c:ùàà() (c:off))
(defun c:ùàâ() (c:ofd))
(defun c:ñê() (c:cr))

(princ "Loaded project edit.\n")
