(setq *fors_rh-command-list* '("ras_har_lic" "ras_har_gas"))
;;;; (opech_cmds-str *fors_rh-command-list*)

(defun c:êôû_ðôê_äøñ() (c:ras_har_lic))
(defun c:êôû_ðôê_ïôû() (c:ras_har_gas))

(princ "Loaded project fors_rh.\n")
