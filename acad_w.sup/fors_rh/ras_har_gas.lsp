;;;(princ "\nЗагружаю Fors_gas/ras_har_gas")
(princ (strcat "\nЗагружаю " (acad_sup) "/" "Fors_gas/ras_har_gas"))

(setq
  ll_ras_har_gas
   (list
     (cons "f_fors" 7.55)
     (cons "ro*dp_min" 0.0)
     (cons "ro*dp_max" 50.0)
     (cons "var_name" "aaaa")
     (cons "n_div" 100)
     (cons "fl" 0)
   )
)

;;;;;;("ras_har_gas" "Вычисление расходной характеристики газовой форсунки." "Расчеты")
(defun c:ras_har_gas (/ fl f_fors n_div ro*dp_max ro*dp_min var_name)
  (setq	dcl_id
	 (load_dialog (strcat (acad_sup) "/fors_rh/fors_rh.dcl"))
  )
  (if (< dcl_id 0)
    (exit)
  )
  (if (not (new_dialog "fors_gas" dcl_id))
    (exit)
  )
  (ras_har_gas:setup)
  (ras_har_gas:ac_tile)
  (setq act (start_dialog))
  (cond
    ((= act 0)     (ras_har_gas:cancel)    )
    ((= act 1)     (ras_har_gas:ok)    )
  )
  (unload_dialog dcl_id)
)

(defun ras_har_gas:setup ()
  (setq
    f_fors    (cdr (assoc "f_fors" ll_ras_har_gas))
    ro*dp_min (cdr (assoc "ro*dp_min" ll_ras_har_gas))
    ro*dp_max (cdr (assoc "ro*dp_max" ll_ras_har_gas))
    var_name  (cdr (assoc "var_name" ll_ras_har_gas))
    n_div     (cdr (assoc "n_div" ll_ras_har_gas))
    fl        (cdr (assoc "fl" ll_ras_har_gas))
  )
  (set_tile "fors_gas:f_fors" (rtos f_fors))
  (set_tile "fors_gas:ro*dp_min" (rtos ro*dp_min))
  (set_tile "fors_gas:ro*dp_max" (rtos ro*dp_max))
  (set_tile "fors_gas:var_name" var_name)
  (set_tile "fors_gas:n_div" (itoa n_div))
  (cond
    ((= fl 0) (set_tile "fors_gas:fl_pr" "1"))
    ((= fl 1) (set_tile "fors_gas:fl_log" "1"))
  )
)


(defun ras_har_gas:cancel ()
  (princ "\nras_har_gas:cancel")
)

(defun ras_har_gas:ok ()
  (princ "\nras_har_gas:ok")
  (setq
    ll_ras_har_gas
     (list
       (cons "f_fors" f_fors)
       (cons "ro*dp_min" ro*dp_min)
       (cons "ro*dp_max" ro*dp_max)
       (cons "var_name" var_name)
       (cons "n_div" n_div)
       (cons "fl" fl)
     )
  )
  (vl-doc-set
    (read var_name)
    (mapcar
      (function
	(lambda	(el)
	  (list el (часовой_расход[кг/ч] f_fors el))
	)
      )
      (sub_div ro*dp_min ro*dp_max n_div fl)
    )
  )
)

(defun часовой_расход[кг/ч](f[мм^2] ro*dp[кг/м^3*бар] / f[м^2] ro*dp[кг/м^3*Па])
  (setq
    f[м^2]	  (* f[мм^2] 1.0e-6)
    ro*dp[кг/м^3*Па] (* ro*dp[кг/м^3*бар] 1.0e5)
  )
  (* 3600.0 f[м^2] (sqrt (* 2.0  ro*dp[кг/м^3*Па])))
)

(defun ras_har_gas:ac_tile ()
  (princ "\nras_har_gas:ac_tile")
  (action_tile "fors_gas:f_fors" "(ras_har_gas:ac-f_fors)")
  (action_tile "fors_gas:ro*dp_min" "(ras_har_gas:ac-ro*dp_min)")
  (action_tile "fors_gas:ro*dp_max" "(ras_har_gas:ac-ro*dp_max)")
  (action_tile "fors_gas:var_name" "(ras_har_gas:ac-var_name)")
  (action_tile "fors_gas:n_div" "(ras_har_gas:ac-n_div)")
  (action_tile "fors_gas:fl_pr" "(ras_har_gas:ac-fl_pr)")
  (action_tile "fors_gas:fl_log" "(ras_har_gas:ac-fl_log)")
)

(defun ras_har_gas:ac-f_fors ()
  (princ "\nras_har_gas:ac-f_fors")
  (setq	f_fors (atof (get_tile "fors_gas:f_fors"))
  )
)

(defun ras_har_gas:ac-ro*dp_min()
  (princ "\nras_har_gas:ac-ro*dp_min")
  (setq	ro*dp_min (atof (get_tile "fors_gas:ro*dp_min")))
)

(defun ras_har_gas:ac-ro*dp_max ()
  (princ "\nras_har_gas:ac-ro*dp_max")
  (setq ro*dp_max (atof (get_tile "fors_gas:ro*dp_max")))
)

(defun ras_har_gas:ac-var_name ()
  (princ "\nras_har_gas:ac-var_name")
  (setq var_name  (get_tile "fors_gas:var_name"))
)

(defun ras_har_gas:ac-n_div	()
  (princ "\nras_har_gas:ac-n_div")
  (setq n_div (atoi (get_tile "fors_gas:n_div")))
)

(defun ras_har_gas:ac-fl_pr()
  (princ "\nras_har_gas:ac-fl_pr")
  (setq fl 0)
)

(defun ras_har_gas:ac-fl_log()
  (princ "\nras_har_gas:ac-fl_log")
  (setq fl 1)
)

(princ "\t...загружен.\n")
;|«Visual LISP© Format Options»
(105 2 15 2 nil "end of" 90 15 0 0 0 T T nil T)
;*** DO NOT add text below the comment! ***|;
