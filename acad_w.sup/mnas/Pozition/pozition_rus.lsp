(setq *position-command-list* '("edpos" "ep" "pozition_set_text_scale" "pos_export"))
;;;;(opech_cmds-str *position-command-list*)

(defun c:σβηωϋ() (c:edpos))
(defun c:ση() (c:ep))
(defun c:ηω�ψεψως_ϋσε_εσχε_ϋρτδσ() (c:pozition_set_text_scale))
(defun c:ηωϋ_σχηωκε() (c:pos_export))

(princ "Loaded project pozitopn.\n")
