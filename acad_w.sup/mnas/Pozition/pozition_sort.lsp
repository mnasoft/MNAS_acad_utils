;;; Сортировка позиций по Машпроектовски
(setq
  s_list '("Б7203295...10 шт."		  "АС02-0643...10 шт."		 "АС6-694...10 шт."
	   "АС7-177...10 шт.&A*16"	  "АС7-203...12 шт.&A*16"	 "АС02-0720...12 шт.&A*28"
	   "АС6-702...6 шт."		  "АС10-1483...6 шт."		 "P59038009...6 шт."
	   "АС2-582...12 шт.&A*28"	  "АС7-179...12 шт.&A*16"
	  )
)

;;;1. Перевод символов на кирилические символы.
;;;1.1 При встрече с символами `&` и `@` следующий за ними символ не транслировать.
;;;2. Разбиение строки позиции на список их трех элементов.
;;;3. Сортировка списка согласно принятой системы сортировки.
;;;3.1 Выделение из строки номера группы, индекса изделия, литеры, номера отдела.
;;;3.1.1 Если номер соответствует шаблону "123456789-ab" или "123456789"
;;;Строка соответствует шаблону 
;;;4. Добавление к списку из трех элементов номеров позиций.
;;;5. Вывод списка позиций в файл.

(defun translate_string(str)
  ()
)

(setq en (car (entsel ":"))
      ed (entget en)
)
(setq
  ed
   (subst_dxf '(
		(300 . "300")
		(301 . "301")
		(302 . "302")
		(303 . "303")
		(304 . "304")
		(14 0.0 1.0 0.0)
		(15 0.0 1.0 0.0)
	       )
	      ed
   )
)
(entmod ed)
(91 . 2968)
;|«Visual LISP© Format Options»
(72 2 5 2 nil "end of" 60 9 0 0 0 T T nil T)
;*** DO NOT add text below the comment! ***|;
