;;;;;;("spl-proj" "Проецирование 3d сплайна на плоскость XY." "Измени")


;;; 1. Замечание - изображается в виде ломаной полилинии ее можно сплайнизировать.
;;; 2. Желательно добавить критерий для определения качества результирующей полилинии.
;;; 3. Желательно добавить возможность улучшения качества приближения
;;; полилинии за счет разбиения сплайна по длине на несколько большее
;;; количество участков чем количество базовых точек сплайна.

(defun c:spl-proj (/ edata pts)
  (setq edata (entget (car (entsel "Выберите сплайн:"))))
  (setq pts nil)
  (mapcar
    (function
      (lambda (el)
	(cond
	  ((= 10 (car el))
	   (setq pts (cons (list (cadr el) (caddr el)) pts))
	  )
	  (t)
	)
      )
    )
    edata
  )
  (dr:pline pts 1)
)
