(setq
  mnasoft-debug	     (vl-doc-ref 'mnasoft-debug)
  mnasoft-debug-path (vl-doc-ref 'mnasoft-debug-path)
)
;|«Visual LISP© Format Options»
(105 2 15 2 nil "end of" 90 9 0 0 0 T T nil T)
;*** DO NOT add text below the comment! ***|;
