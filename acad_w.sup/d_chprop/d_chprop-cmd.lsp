(vl-arx-import 'acad_colordlg)

;;;;;;("dch" "Программа управления свойствами объектов." "Измени")
(defun c:dch  (/ *error* action	by_block by_layer color1 color4	dcl_id do_dialog ename1	err layer1 layer4 ltype1 ltype4
	       old_err)
  (setq	old_err	*error*
	*error*	err)
  (setvar "cmdecho" 0)
  (command "_undo" "_group")
  (cond	((= (substr (ver) 1 8) "AutoLISP")
	 (setq by_layer	"BYLAYER"
	       by_block	"BYBLOCK"))
	((= (substr (ver) 1 8) "Автолисп")
	 (setq by_layer	"ПОСЛОЮ"
	       by_block	"ПОБЛОКУ"))
	(t
	 (setq by_layer	"BYLAYER"
	       by_block	"BYBLOCK")
	 (princ t)))
  (setq dcl_id (load_dialog (findfile "acad_w.sup/d_chprop/d_chprop.dcl")))
  (if (< dcl_id 0)
    (exit))
  (setq do_dialog t)
  (while do_dialog
    (if	(not (new_dialog "dchprop" dcl_id))
      (exit))
    (if	(equal layer1 nil)
      (setq layer1 (getvar "clayer")))
    (if	(equal ltype1 nil)
      (setq ltype1 (getvar "celtype")))
    (if	(equal color1 nil)
      (setq color1 (getvar "cecolor")))
    (if	layer4
      (set_tile "a7" layer4)
      (set_tile "a7" (setq layer4 "1")))
    (if	ltype4
      (set_tile "a8" ltype4)
      (set_tile "a8" (setq ltype4 "1")))
    (if	color4
      (set_tile "a9" color4)
      (set_tile "a9" (setq color4 "1")))
    (set_tile "a10" layer1)
    (set_tile "a11" ltype1)
    (set_tile "a12" color1)
    (action_tile "a1" "(done_dialog 2)")
    (action_tile "a4" "(ac-4)")
    (action_tile "a5" "(ac-5)")
    (action_tile "a6" "(ac-6)")
    (action_tile "a7" "(ac-7)")
    (action_tile "a8" "(ac-8)")
    (action_tile "a9" "(ac-9)")
    (action_tile "a10" "(ac-10)")
    (action_tile "a11" "(ac-11)")
    (action_tile "a12" "(ac-12)")
    (action_tile "a13" "(done_dialog 13)")
    (action_tile "a14" "(ac-14)")
    (action_tile "a15" "(ac-15)")
    (action_tile "a16" "(done_dialog 16)")
    (action_tile "a17" "(ac-17)")
    (action_tile "a18" "(ac-18)")
    (action_tile "a19" "(ac-19)")
    (action_tile "a20" "(about)")
    (setq action (start_dialog))
    (cond ((= action 0) (setq do_dialog nil))
	  ((= action 1) (ac-1) (setq do_dialog nil))
	  ((= action 2) (setq ename1 (ssget)))
	  ((= action 3) (setq ename1 (ssget)))
	  ((= action 13) (ac-13))
	  ((= action 16) (ac-1)))	;cond
    )
  (unload_dialog dcl_id)
  (command "_undo" "_end")
  (setvar "cmdecho" 1)
  (princ))

(defun ac-1  ()
  (if ename1
    (progn (command "_chprop" ename1 "")
	   (if (= layer4 "1")
	     (command "_la" layer1))
	   (if (= ltype4 "1")
	     (command "_lt" ltype1))
	   (if (= color4 "1")
	     (command "_c" color1))
	   (command ""))))

(defun ac-4  (/ q dcl_id)
  (defun q (i) (cdr (assoc 2 i)))
  (setq dcl_id (load_dialog (findfile "acad_w.sup/d_chprop/d_chprop.dcl")))
  (if (< dcl_id 0)
    (exit))
  (if (not (new_dialog "layertype" dcl_id))
    (exit))
  (setq layer2 (tblnext "layer" 0))
  (setq layer3 (cons layer2 (setq layer3 nil)))
  (while (setq layer2 (tblnext "layer")) (setq layer3 (cons layer2 layer3)))
  (setq layer2 (reverse (mapcar 'q layer3)))
  (start_list "c4")
  (mapcar 'add_list layer2)
  (end_list)
  (set_tile "c5" (setq layer3 layer1))
  (action_tile "c4" "(cc_4 $value)")
  (setq action_1 (start_dialog))
  (cond ((= action_1 1) (setq layer1 layer3) (set_tile "a10" layer3)))
  (unload_dialog dcl_id))

(defun ac-5  (/ q dcl_id)
  (defun q (i) (cdr (assoc 2 i)))
  (setq dcl_id (load_dialog (findfile "acad_w.sup/d_chprop/d_chprop.dcl")))
  (if (< dcl_id 0)
    (exit))
  (if (not (new_dialog "linetype" dcl_id))
    (exit))
  (setq ltype2 (tblnext "ltype" 0))
  (setq ltype3 (cons ltype2 (setq ltype3 nil)))
  (while (setq ltype2 (tblnext "ltype")) (setq ltype3 (cons ltype2 ltype3)))
  (setq ltype2 (reverse (mapcar 'q ltype3)))
  (setq ltype2 (cons by_block ltype2))
  (setq ltype2 (cons by_layer ltype2))
  (start_list "b4")
  (mapcar 'add_list ltype2)
  (end_list)
  (set_tile "b7" (setq ltype3 ltype1))
  (action_tile "b4" "(bc_4 $value)")
  (action_tile "b7" "(bc_7)")
  (setq action_1 (start_dialog))
  (cond ((= action_1 1) (setq ltype1 ltype3) (set_tile "a11" ltype1)))
  (unload_dialog dcl_id))

(defun ac-6  ()
  (setq color2 (acad_colordlg 1 t))
  (cond	((= (type color2) 'INT)
	 (if (and (> color2 0) (< color2 256))
	   (setq color1 (itoa color2)))
	 (if (= color2 0)
	   (setq color1 by_block))
	 (if (= color2 256)
	   (setq color1 by_layer))))
  (set_tile "a12" color1))

(defun ac-7 () (setq layer4 (get_tile "a7")))

(defun ac-8 () (setq ltype4 (get_tile "a8")))

(defun ac-9 () (setq color4 (get_tile "a9")))

(defun ac-10  (/ layer2)
  (setq layer2 (strcase (get_tile "a10")))
  (if (tblsearch "layer" layer2)
    (setq layer1 layer2))
  (set_tile "a10" layer1))

(defun ac-11  (/ ltype2)
  (setq ltype2 (strcase (get_tile "a11")))
  (if (= ltype2 "_BYLAYER")
    (setq ltype2 by_layer))
  (if (= ltype2 "_BYBLOCK")
    (setq ltype2 by_block))
  (if (or (= ltype2 by_block) (= ltype2 by_layer))
    (setq ltype1 ltype2)
    (if	(tblsearch "ltype" ltype2)
      (setq ltype1 ltype2)))
  (set_tile "a11" ltype1))

(defun ac-12  (/ color2 color3)
  (setq color2 (strcase (get_tile "a12")))
  (if (= color2 "_BYLAYER")
    (setq color2 by_layer))
  (if (= color2 "_BYBLOCK")
    (setq color2 by_block))
  (if (or (= color2 by_block)
	  (= color2 by_layer)
	  (= color2 "_RED")
	  (= color2 "КРАСНЫЙ")
	  (= color2 "_YELLOW")
	  (= color2 "ЖЕЛТЫЙ")
	  (= color2 "_GREEN")
	  (= color2 "ЗЕЛЕНЫЙ")
	  (= color2 "_CYAN")
	  (= color2 "ГОЛУБОЙ")
	  (= color2 "_BLUE")
	  (= color2 "СИНИЙ")
	  (= color2 "_MAGENTA")
	  (= color2 "ФИОЛЕТ."))
    (setq color1 color2)
    (progn (setq color3 (atoi color2))
	   (if (and (> color3 0) (< color3 256))
	     (setq color1 (itoa color3)))))
  (set_tile "a12" color1))

(defun ac-13  ()
  (setq ename2 (car (entsel "\nУкажите объект :")))
  (if ename2
    (progn (setq edata2 (entget ename2))
	   (setq layer2 (cdr (assoc 8 edata2)))
	   (setq ltype2 (cdr (assoc 6 edata2)))
	   (setq color2 (cdr (assoc 62 edata2)))
	   (cond ((equal color2 nil) (setq color1 by_layer))
		 ((= (type color2) 'INT)
		  (if (> color2 0)
		    (setq color2 (itoa color2))
		    (setq color2 by_block))))
	   (if (= layer4 "1")
	     (setq layer1 layer2))
	   (if (= ltype4 "1")
	     (setq ltype1 ltype2))
	   (if (= color4 "1")
	     (setq color1 color2)))))

(defun ac-14  ()
  (if (= layer4 "1")
    (set_tile "a10" (setq layer1 (getvar "clayer"))))
  (if (= ltype4 "1")
    (set_tile "a11" (setq ltype1 (getvar "celtype"))))
  (if (= color4 "1")
    (set_tile "a12" (setq color1 (getvar "cecolor")))))

(defun ac-15  ()
  (if (= color4 "1")
    (setvar "cecolor" color1))
  (if (= layer4 "1")
    (setvar "clayer" layer1))
  (if (= ltype4 "1")
    (setvar "celtype" ltype1)))

(defun ac-17  ()
  (if (tblsearch "ltype" "center")
    (set_tile "a11" (setq ltype1 "CENTER")))
  (set_tile "a12" (setq color1 "7")))

(defun ac-18 () (set_tile "a11" (setq ltype1 by_layer)) (set_tile "a12" (setq color1 "7")))

(defun ac-19 () (set_tile "a11" (setq ltype1 by_layer)) (set_tile "a12" (setq color1 by_layer)))

(defun about () (alert (strcat "Редактирование свойств" (about-GPL-string))))

(defun bc_4 (value) (set_tile "b7" (setq ltype3 (nth (atoi value) ltype2))))

(defun cc_4 (value) (set_tile "c5" (setq layer3 (nth (atoi value) layer2))))

(defun err (msg) (setq *error* old_err) (princ))
