;;;;;;("obj" "Возвращает данные выбранного примитива." "Объекты")
(defun c:obj () (vl-doc-set 'obj (entget (car (entsel "\nВыберите примитив:")))))

;;;;;;("nobj" "Возвращает данные выбранного подпримитива." "Объекты")
(defun c:nobj () (vl-doc-set 'nobj (entget (car (nentsel "\nВыберите примитив:")))))

;;;;;;("objxd"
;;;;;;"Возвращает данные и расширенные данные выбранного примитива." "Объекты")
(defun c:objxd () (vl-doc-set 'objxd (entget (car (entsel "\nВыберите примитив:")) (list "*"))))

;;;;;;("nobjxd"
;;;;;;"Возвращает данные и расширенные данные выбранного подпримитива." "Объекты")
(defun c:nobjxd () (vl-doc-set 'nobjxd (entget (car (nentsel "\nВыберите примитив:")) (list "*"))))
