(setq MNAS_function_help '(("select_column" "Выполняет выборку из списка, указанных столбцыов.\nАргументы:matrix - список, состояший из списков.\nlst    - список, содержащий номера отбираемых столбцов.\nПример использования:_$ (select_column '((0.0 -10.0 -1.0 -2.0)      (1.0 -9.0 -0.9 -1.377)      (2.0 -8.0 -0.8 -0.896)      (3.0 -7.0 -0.7 -0.539)      (4.0 -6.0 -0.6 -0.288)      (5.0 -5.0 -0.5 -0.125)     )    '(3 1))" "D:/Develop/MNAS_acad_utils/acad_w.sup/exel/graph.lsp")("g_usp()" "Ускорение свободного падения[м/с^2]." "D:/Develop/MNAS_acad_utils/acad_w.sup/funktcii/Fizichjeskije/Phizich.lsp")("T_abs0[C] ()" "Абсолютный ноль в градусах цельсиях." "D:/Develop/MNAS_acad_utils/acad_w.sup/funktcii/Fizichjeskije/Phizich.lsp")("T[K]->t[C] ( T[K] )" "Перевод температуры из кельвинов в градусы цельсия." "D:/Develop/MNAS_acad_utils/acad_w.sup/funktcii/Fizichjeskije/Phizich.lsp")("t[C]->T[K] (t[C])" "Перевод температуры из градусов цельсия в кельвины." "D:/Develop/MNAS_acad_utils/acad_w.sup/funktcii/Fizichjeskije/Phizich.lsp")("p_atm ()" "Нормальное атмосферное давление [Па]." "D:/Develop/MNAS_acad_utils/acad_w.sup/funktcii/Fizichjeskije/Phizich.lsp")("kg/cm2->Pa (kg/cm2)" "Перевод давления из кг/см^2 в Па." "D:/Develop/MNAS_acad_utils/acad_w.sup/funktcii/Fizichjeskije/Phizich.lsp")("Pa->kg/cm2 (Pa)" "Перевод давления из Па в кг/см^2." "D:/Develop/MNAS_acad_utils/acad_w.sup/funktcii/Fizichjeskije/Phizich.lsp")("p_izb->p_abs( p_izb )" "Перевод избыточного давления в абсолютное [Па]." "D:/Develop/MNAS_acad_utils/acad_w.sup/funktcii/Fizichjeskije/Phizich.lsp")("p_izb[kg/cm2]->p_abs[Pa] ( p_izb )" "Перевод избыточного давления [кг/см^2] в абсолютное [Па]." "D:/Develop/MNAS_acad_utils/acad_w.sup/funktcii/Fizichjeskije/Phizich.lsp")("ro(P mu Rmu Temperatura)" "Плотность по P mu Rmu Temperatura" "D:/Develop/MNAS_acad_utils/acad_w.sup/funktcii/Fizichjeskije/Phizich.lsp")("string-subst-all(new_substr olg_sustr str)" "Производит замену всех вхождений olg_sustr на new_substr для строки str." "D:/Develop/MNAS_acad_utils/acad_w.sup/funktcii/Regystry/registry.lsp")("tbl_to_xls" "Вывод таблицы в html формате" "D:/Develop/MNAS_acad_utils/acad_w.sup/graf/point_to_xsl.LSP")("uroven" (STRCAT "Определение гидростатического уровня i-той форсуки в коллекторе.\n" "Параметры:\n" "i      - номер форсунки в коллекторе;\n" "n      - количество форсунк в коллекторе;\n" "d_koll - диаметр коллектора.\n") "D:/Develop/MNAS_acad_utils/acad_w.sup/kollector/kollector.lsp")("P_Arxided" "Архимедово давление, кгс/см2.\n h - высота, отсчитываемая от нижней точки коллектора." "D:/Develop/MNAS_acad_utils/acad_w.sup/kollector/kollector.lsp")("p_i" "Давление перед i-той форсункой\n Параметры: dP[кгс/см2] - перепад давления на коллекторе в его нижней части; i           - номер форсунки, отсчитываемый от горизонтали первая форсунка имее номер 0;\n n           - количество форсунок в коллекторе; d_koll[м]   - диаметр коллектора; ro[кг/м3]   - плотность топлива; " "D:/Develop/MNAS_acad_utils/acad_w.sup/kollector/kollector.lsp")("g_i" "Расход топлива через форсунку." "D:/Develop/MNAS_acad_utils/acad_w.sup/kollector/kollector.lsp")("g_sum" "Возвращает список с расходами через форсунки в коллекторе. Параметры:\n dp - перепад давления на форсунке, [кгс/см2];\n n - количество форсунок в коллекторе;\n d_koll - диаметр коллектора, [м];\n ro - полтность топлива, [кг/м3];\n dp_k - перепад давления в контрольной кочке, [кгс/см2];\n ro_k - плотность топлива при контрольной проливке, [кг/м3];\n G_k - расход топлива при контрольной проливке одной форсунки, [кг/ч].\n Пример использования: (g_sum 0.08 16 1.0 835. 30. 835. 334.) " "D:/Develop/MNAS_acad_utils/acad_w.sup/kollector/kollector.lsp")("get_center_lines" "Возвращает набор выбора из отрезков, имеющих осевой тип линии.Пример использования:(get_center_lines)<Selection set: db>" "D:/Develop/MNAS_acad_utils/acad_w.sup/lines/LINE_1.lsp")("get_cut_edges" "Возвращает набор выбора из отрезков, дуг, окружностей, полилиний, эллипсов, имеющих не осевой тип линии.Пример использования:(get_cut_edges)<Selection set: df>" "D:/Develop/MNAS_acad_utils/acad_w.sup/lines/LINE_1.lsp")("v3d->list" "Выполняет преобразование vla3d точки в список её координат." "D:/Develop/MNAS_acad_utils/acad_w.sup/lines/line_concat.lsp")("is-collinear" "Выполняет проверку двух отрезков на коллинеарность. Возвращает: T - отрезки коллинеарны; nil - отрезки не коллинеарны. Параметры: v_line_1 - Vla объект, представляющй первый отрезок; v_line_2 - Vla объект, представляющй второй отрезок; delta - точность, расстояние от точки до отрезка при котором объекты считаются коллинеарными. Пример использования: (vl-load-com) (entmake '((0 . \"LINE\") (10 0.0 0.0 0.0) (11 10.0 10.0 0.0))) (setq vl1 (vlax-ename->vla-object(entlast))) (entmake '((0 . \"LINE\") (10 20.0 20.0 0.0) (11 30.0 30.0 0.0))) (setq vl2 (vlax-ename->vla-object(entlast))) (entmake '((0 . \"LINE\") (10 25.0 20.0 0.0) (11 35.0 30.0 0.0))) (setq vl3 (vlax-ename->vla-object(entlast))) (is-collinear vl1 vl2 0.0001) (is-collinear vl1 vl3 0.0001) " "D:/Develop/MNAS_acad_utils/acad_w.sup/lines/line_concat.lsp")("concatenate_two_lines" " Выполняет объединение двух отрезков. Возвращает список из удаляемых отрезков. Параметры. v_line_1 - Vla объект, предвтавляющий первый отрезок v_line_2 - Vla объект, предвтавляющий второй отрезок delta - Точность, максимальное расстояние между точкой и отрезком при котором они считаются совпадающими filter " "D:/Develop/MNAS_acad_utils/acad_w.sup/lines/line_concat.lsp")("man-rebuild" "Prj - man.\nFile - man.lsp.Производит извлечение справочной информации из файлов *.lsp" "D:/Develop/MNAS_acad_utils/acad_w.sup/man/man.lsp")("dir_recursive" "Рекурсивный поиск всех каталогов начиная с каталога directory." "D:/Develop/MNAS_acad_utils/acad_w.sup/man/man.lsp")("fname_recursive" "Рекурсивный поиск всех имен файлов с маской fn_mask начиная с каталога directory." "D:/Develop/MNAS_acad_utils/acad_w.sup/man/man.lsp")("find_line_by_mask" "Производит поиск строк в файле с именем fname,\nудовлетворяющих маске mask и производит их запись в файл с дескриптором  f_out.\nФайл f_out должен быть открыт по записи." "D:/Develop/MNAS_acad_utils/acad_w.sup/man/man.lsp")("find-line-by_mask-in_directory_files" "Производит поиск строк, удовлетворяющих маске str_mask,\nв файлах с маской имени файла file_mask\nначиная с коталога directory рекурсивно вглубь по дереву каталогов\nи выводит строки, найденные в файлах, в выходной файл с именем fn_out." "D:/Develop/MNAS_acad_utils/acad_w.sup/man/man.lsp")("w-edit-arrow-dir" "D:/Develop/MNAS_acad_utils/acad_w.sup/mnas/Welding_lsp/get_dimstyle_hanlde.lsp")("registry-dir" "Выполняет чтение подключей для строк содержащих ключи реестра.\nВозвращает список подключей реестра.\nПараметры:\nstr-lst - содержит список ключей реестра.\nПример использования 1:\n(registry-dir '(\"HKEY_LOCAL_MACHINE\\SOFTWARE\\Autodesk\\AutoCAD\\R17.2\\ACAD-7005:419\\Applications\\MNASArx_Pozition\"))\nРезультат работы 1:\n'(\"HKEY_LOCAL_MACHINE\\SOFTWARE\\Autodesk\\AutoCAD\\R17.2\\ACAD-7005:419\\Applications\\MNASArx_Pozition\\Groups\"\n  \"HKEY_LOCAL_MACHINE\\SOFTWARE\\Autodesk\\AutoCAD\\R17.2\\ACAD-7005:419\\Applications\\MNASArx_Pozition\\Commands\"\n )\n" "D:/Develop/MNAS_acad_utils/acad_w.sup/M_utils_loader/M_utils_loader.lsp")("equal_area_radius" "Делит кольцо между максимальным радиусом rb и минимальным радиусом rm на n равновеликих по площади частей и выводит i-товый радиус. При значении i=0 выводится внутренний радиус. При значении i=n выводится наружный радиус. rb > rm. Наример, для того чтобы рассчитать радиусы для постановки 5-ти термопар при rm=802.0;   rb 871.5. Необходимо выполнить следующее: (equal_area_radius 871.5 802.0 1 10) (equal_area_radius 871.5 802.0 3 10) (equal_area_radius 871.5 802.0 5 10) (equal_area_radius 871.5 802.0 7 10) (equal_area_radius 871.5 802.0 9 10)" "D:/Develop/MNAS_acad_utils/acad_w.sup/tmp/equal_area.lsp")("equal_area_radius_n" "Делит кольцо между максимальным радиусом rb и минимальным радиусом rm на n равновеликих по площади частей и выводит их радиусы.  rb > rm. Наример, для того чтобы рассчитать радиусы для постановки 5-ти термопар при rm=802.0;   rb 871.5. Неодходимо выполнить следующее:(equal_area_radius_n 871.5 802.0 5)" "D:/Develop/MNAS_acad_utils/acad_w.sup/tmp/equal_area.lsp")("ss_to_list" "Преобразует набор примитивов в список, содержащий имена примитивов." "D:/Develop/MNAS_acad_utils/acad_w.sup/utils/ASIST.lsp")("list_to_ss" "Преобразует список, содержащий имена примитивов в набор примитивов." "D:/Develop/MNAS_acad_utils/acad_w.sup/utils/ASIST.lsp")("Space()" "Space определяет какое пространство (модели или листа) является текущим.\nВозвращает:\n1. nil - если текущим является пространство листа;\n2. t   - если текущим является пространство модели." "D:/Develop/MNAS_acad_utils/acad_w.sup/utils/draw.lsp")("AcadAppDocSpace()" "Создает глобальные переменные содержащие vla-объекты:\n1. Приложения Acad - *acad-App;\n2. Активного документа - *acad-Doc;\n3. Текущего пространства модели - *acad-M-Space;\n4. Текущего пространства листа - *acad-P-Space.\nВозвращает указатель на текущее пространство (модели или листа)." "D:/Develop/MNAS_acad_utils/acad_w.sup/utils/draw.lsp")("dr:ch_prop(prop)" "dr:ch_prop(prop) - изменение свойств последнего созданного объекта.\n(dr:ch_prop  '(( 8 . " 1 ")(62 . 1)))" "D:/Develop/MNAS_acad_utils/acad_w.sup/utils/draw.lsp")("dr:point(pt col)" "Создает точку в текущем прострпнстве.\n   p - список, содержащий координаты точки;\n   col - номер цвета, создаваемой точки.\n(dr:point '(0.0 0.0 0.0) 2)\n#<VLA-OBJECT IAcadPoint 0ed61fa4>" "D:/Develop/MNAS_acad_utils/acad_w.sup/utils/draw.lsp")("dr:line(pt1 pl2 col)" "Создает отрезок в текущем пространстве.\n   pt1 - начальная точка отрезка;\n   pt2 - конечная точка отрезка;\n   col - цвет отрезка.\n_$ (dr:line '(0.0 0.0 0.0) '(10.0 10.0 0.0) 256)\n#<VLA-OBJECT IAcadLine 00f6c154>\nВозвращает vla-объект, соответствующий нарисованному отрезку." "D:/Develop/MNAS_acad_utils/acad_w.sup/utils/draw.lsp")("dr:pline(pts col)" "Создает полилинию в текущем пространстве.\nЭта полилиния может состоять только из прямолинейных сегментов.\n   pts - список 2d точек;\n   col - цвет полилинии.\n_$ (dr:pline '((0.0 0.0) (10.0 10.0)(20.0 15.0)(30.0 5.0)) 1 )\n#<VLA-OBJECT IAcadLWPolyline 0ed63ec4>\nВозвращает vla-объект, соответствующий нарисованной полилинии." "D:/Develop/MNAS_acad_utils/acad_w.sup/utils/draw.lsp")("dr:circle(pt r col)" "Создает окружность в текущем пространстве.\n   pt  - центр окружности;   r   - радиус окружности;   col - номер цвета  окружности._$ (dr:circle '(0.0 0.0 0.0) 10.0 256)\n#<VLA-OBJECT IAcadCircle 0ed63fa4>\nВозвращает vla-объект, соответствующий нарисованной окружности.\n" "D:/Develop/MNAS_acad_utils/acad_w.sup/utils/draw.lsp")("set-sys-var-lst (variable-lst)" "Устанавливает значения системных переменных\nvariable-lst - список, каждый элемент которого должен содержать список, состоящий из:1 строки - пердставляющей системную переменную ACAD;2 значения, которое устанавливается для этой системной переменной.(set-sys-var-lst '((\"cmdecho\" 1) (\"orthomode\" 0)))" "D:/Develop/MNAS_acad_utils/acad_w.sup/utils/ERR.lsp")("get-sys-var-lst (variable-lst)" "Считывает значения системных переменных\nvariable-lst - список, каждый элемент которого строка - являющаяся системной переменной ACAD.(get-sys-var-lst '(\"cmdecho\" \"orthomode\" ))" "D:/Develop/MNAS_acad_utils/acad_w.sup/utils/ERR.lsp")("print-to-string" "Производит вывод цитируемого значения $val в строку,в виде пригодном для последующего восстановдения значения функцией load-from-string.(setq value 1.0) (print-to-string 'value)1.0(setq VALUE '1.0)" "D:/Develop/MNAS_acad_utils/acad_w.sup/utils/system_registry.lsp")("devide-list" "Разбивает список lst на группы по n элементов." "D:/Develop/MNAS_acad_utils/acad_w.sup/utils/vla-utils.lsp")("pnt-distance-short" "Возвращает точку из списка точек pnt-lst-to,\nрасстояние до которой от точки pnt-from является наименьшим." "D:/Develop/MNAS_acad_utils/acad_w.sup/utils/vla-utils.lsp")))
