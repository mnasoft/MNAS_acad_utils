(setq *man-command-list* '("check_command_category_list" "man"))
;;;; (opech_cmds-str *man-command-list*)

(defun c:срусл_сщььфтв_сфеупщкн_дшые() (c:check_command_category_list))
(defun c:ьфт() (c:man))

(princ "Loaded project man.\n")
