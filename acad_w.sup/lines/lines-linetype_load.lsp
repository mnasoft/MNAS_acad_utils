;;;;;;("ltp" "Загрузка шрифтов линий." "Настройка")
(defun c:ltp  ()
  (command "_ltscale" "1")
  (command "_psltscale" "1")
  (command "_-linetype" "_load" "*" (findfile "acad_w.sup/lines/eskd.lin"))
  (while (= 1 (getvar "CMDACTIVE")) (command ""))
  (command "_regen")
  (princ))
