(defun lo:draw_lop  ()
  (lo:lop_1)
  (lo:lop_2)
  (lo:lop_3)
  (lo:lop_4)
  (lo:lop_5)
  (lo:lop_6)
  (princ))

(defun lo:lop_1	 ()
  (setq pi2 (/ pi 2.0))
  (setq p1_00 (polar p1_01 0.0 h))
  (setq p1_1 (polar p1_01 pi2 r1))
  (setq p1_2 (polar p1_1 a1 (/ (- r2 r1) (sin a1))))
  (setq p1_3 (polar p1_2 (+ a1 pi2) h))
  (setq p1_4 (polar p1_1 (+ a1 pi2) h))
  (dr:line p1_1 p1_2 256)
  (dr:line p1_3 p1_2 256)
  (dr:line p1_3 p1_4 256)
  (dr:line p1_1 p1_4 256)
  (setq p1_02 (inters p1_00 p1_01 p1_2 (polar p1_2 pi2 h) nil))
  (setq p1_03 (inters p1_00 p1_01 p1_3 (polar p1_3 pi2 h) nil))
  (setq p1_04 (inters p1_00 p1_01 p1_4 (polar p1_4 pi2 h) nil))
  (setq r3 (distance p1_3 p1_03))
  (setq r4 (distance p1_4 p1_04))
  (dr:line p1_01 p1_1 256)
  (dr:line p1_02 p1_2 256)
  (dr:line p1_03 p1_3 256)
  (dr:line p1_04 p1_4 256)
  (princ))

(defun lo:lop_2	 ()
  (setq p2_00 (polar p2_0 (- a1 pi2) h))
  (setq p2_1 (ac2_2 p1_1))
  (setq p2_2 (ac2_2 p1_2))
  (setq p2_3 (ac2_2 p1_3))
  (setq p2_4 (ac2_2 p1_4))
  (setq p2_1c (ac2_2 p1_01))
  (setq p2_2c (ac2_2 p1_02))
  (setq p2_3c (ac2_2 p1_03))
  (setq p2_4c (ac2_2 p1_04))
  (setq p2_01 (ac2_3 p1_01 r1))
  (setq p2_02 (ac2_3 p1_02 r2))
  (setq p2_03 (ac2_3 p1_03 r3))
  (setq p2_04 (ac2_3 p1_04 r4))
  (command "_.ucs" "_w")
  (ac2_4 p2_1c p2_01 p2_1)
  (ac2_4 p2_2c p2_02 p2_2)
  (ac2_4 p2_3c p2_03 p2_3)
  (ac2_4 p2_4c p2_04 p2_4)
  (command "_.ucs" "_p")
  (princ))
(defun ac2_2 (p1) (inters p2_0 p2_00 p1 (polar p1 a1 h) nil))
(defun ac2_3 (p1 r1) (polar (inters p2_0 p2_00 p1 (polar p1 a1 h) nil) a1 r1))
(defun ac2_4 (_1c _01 _1) (command "_.ellipse" "_c" "_non" _1c "_non" _01 "_non" _1))

(defun lo:lop_3	 ()
  (setq p3_c (inters p1_01 (polar p1_01 0.0 h) p3_0 (polar p3_0 pi2 h) nil))
  (setq p3_1 (ac3_1 p1_1))
  (setq p3_2 (ac3_1 p1_2))
  (setq p3_3 (ac3_1 p1_3))
  (setq p3_4 (ac3_1 p1_4))
  (dr:circle p3_c r1 256)
  (dr:circle p3_c r2 256)
  (dr:circle p3_c r3 256)
  (dr:circle p3_c r4 256)
  (princ))
(defun ac3_1 (p1) (inters p3_0 (polar p3_0 pi2 h) p1_3 (polar p1 0.0 h) nil))

(defun lo:lop_4	 ()
  (setq p2_5 (polar (polar p2_3 (- a1 pi2) l2) (+ pi a1) l1))
  (setq p2_6 (polar p2_5 (- (+ a1 a2) pi) r_1))
  (setq p2_7 (polar p2_6 (- (+ a1 a2) pi2) h))
  (setq p2_8 (polar p2_5 (+ a1 a3) r_1))
  (setq p2_9 (polar p2_8 (- (+ a1 a3) pi2) h))
  (setq p2_7_1 (ac_12_2 p2_6 p2_7 p2_1c p2_1 p2_01))
  (setq p2_7_2 (ac_12_2 p2_6 p2_7 p2_2c p2_2 p2_02))
  (setq p2_6_3 (ac_12_2 p2_6 p2_7 p2_3c p2_3 p2_03))
  (setq p2_6_4 (ac_12_2 p2_6 p2_7 p2_4c p2_4 p2_04))
  (setq p2_9_1 (ac_12_2 p2_8 p2_9 p2_1c p2_1 p2_01))
  (setq p2_9_2 (ac_12_2 p2_8 p2_9 p2_2c p2_2 p2_02))
  (setq p2_8_3 (ac_12_2 p2_8 p2_9 p2_3c p2_3 p2_03))
  (setq p2_8_4 (ac_12_2 p2_8 p2_9 p2_4c p2_4 p2_04))
  (dr:circle p2_5 r_1 4)
  (dr:line p2_6 p2_7_1 1)
  (dr:line p2_8 p2_9_1 2)
  (setq p3_7_1 (loac4_1 p1_1 p1_01 p2_7_1))
  (setq p3_7_2 (loac4_1 p1_2 p1_02 p2_7_2))
  (setq p3_6_3 (loac4_1 p1_3 p1_03 p2_6_3))
  (setq p3_6_4 (loac4_1 p1_4 p1_04 p2_6_4))
  (setq p3_9_1 (loac4_1 p1_1 p1_01 p2_9_1))
  (setq p3_9_2 (loac4_1 p1_2 p1_02 p2_9_2))
  (setq p3_8_3 (loac4_1 p1_3 p1_03 p2_8_3))
  (setq p3_8_4 (loac4_1 p1_4 p1_04 p2_8_4))
  (dr:line p3_7_2 p3_6_3 1)
  (dr:line p3_6_4 p3_6_3 1)
  (dr:line p3_6_4 p3_7_1 1)
  (dr:line p3_7_2 p3_7_1 1)
  (dr:line p3_9_2 p3_8_3 2)
  (dr:line p3_8_4 p3_8_3 2)
  (dr:line p3_8_4 p3_9_1 2)
  (dr:line p3_9_2 p3_9_1 2)
  (princ))
(defun loac4_1	(p1_1 p1_01 p2_7_1 / p1_7_1 p2_7_01 p3_7_01)
  (setq p1_7_1 (inters p1_1 p1_01 p2_7_1 (polar p2_7_1 a1 h) nil))
  (setq p2_7_01 (inters p1_7_1 p2_7_1 p2_0 (polar p2_0 (- a1 pi2) h) nil))
  (setq p3_7_01 (inters p1_7_1 (polar p1_7_1 0.0 h) p3_0 (polar p3_0 pi2 h) nil))
  (polar p3_7_01 (- (angle p2_7_01 p2_7_1) a1) (distance p2_7_01 p2_7_1)))
(defun ac_12_2	(_6 _7 _4c _4 _04 / e_6 e_7 x2 y2 x1 y1 m_r)
  (setq e_6 (m_r _6 _4c (- pi2 a1)))
  (setq e_7 (m_r _7 _4c (- pi2 a1)))
  (ac_12 e_6 e_7 (distance _4c _4) (distance _4c _04))
  (polar (polar _4c (- a1 pi2) x2) a1 y2))
(defun ac_12  (p1 p2 ax by / k l ac_1 a b c)
  (ac_1 p1 p2)
  (setq a (+ (/ 1 (* ax ax)) (/ (* k k) (* by by))))
  (setq b (/ (* 2 k l) (* by by)))
  (setq c (- (/ (* l l) (* by by)) 1))
  (setq x1 (ur_kv_1 a b c))
  (setq y1 (+ l (* k x1)))
  (setq x2 (ur_kv_2 a b c))
  (setq y2 (+ l (* k x2))))
(defun ac_1  (p1_0 p1_1)
  (setq k (/ (- (cadr p1_1) (cadr p1_0)) (- (car p1_1) (car p1_0))))
  (setq l (- (cadr p1_0) (* k (car p1_0)))))
(defun ur_kv_1	(a b c)
  (setq d (- (* b b) (* 4 a c)))
  (if (>= d 0)
    (/ (+ (- b) (sqrt d)) (* 2 a))
    (princ "\nУравнение не имеет действительных корней!")))
(defun ur_kv_2	(a b c)
  (setq d (- (* b b) (* 4 a c)))
  (if (>= d 0)
    (/ (- (- b) (sqrt d)) (* 2 a))
    (princ "\nУравнение не имеет действительных корней!")))
(defun m_r  (p p0 a / x y x0 y0 c_a s_a)
  (setq	x   (car p)
	y   (cadr p)
	x0  (car p0)
	y0  (cadr p0)
	c_a (cos a)
	s_a (sin a))
  (list (- (* (- x x0) c_a) (* (- y y0) s_a)) (+ (* (- x x0) s_a) (* (- y y0) c_a)) 0.0))


(defun lo:lop_5	 (/ ac5_1)
  (defun ac5_1	(p3_7_1 p1_1 p1_01 / p3_7r1 p1_7r1 p2_7r01)
    (setq p3_7r1 (polar p3_c (+ (angle p3_c p3_7_1) (/ pi 0.5 n)) (distance p3_c p3_7_1)))
    (setq p1_7r1 (inters p3_7r1 (polar p3_7r1 0.0 h) p1_1 p1_01 nil))
    (setq p2_7r01 (inters p1_7r1 (polar p1_7r1 a1 h) p2_0 (polar p2_0 (- a1 pi2) h) nil))
    (polar p2_7r01 (- a1 pi) (- (car p3_c) (car p3_7r1))))
  (setq p2_9r1 (ac5_1 p3_9_1 p1_1 p1_01))
  (setq p2_9r2 (ac5_1 p3_9_2 p1_2 p1_02))
  (setq p2_8r3 (ac5_1 p3_8_3 p1_3 p1_03))
  (setq p2_8r4 (ac5_1 p3_8_4 p1_4 p1_04))
  (dr:line p2_8r3 p2_9r2 2)
  (dr:line p2_9r1 p2_8r4 2)
  (setq p2_7r1 (ac5_1 p3_7_1 p1_1 p1_01))
  (setq p2_7r2 (ac5_1 p3_7_2 p1_2 p1_02))
  (setq p2_6r3 (ac5_1 p3_6_3 p1_3 p1_03))
  (setq p2_6r4 (ac5_1 p3_6_4 p1_4 p1_04))
  (dr:line p2_6r3 p2_7r2 1)
  (dr:line p2_7r1 p2_6r4 1)
  (princ))

(defun lo:lop_6	 (/ hl lk lp f1 p2_9r1_1 p2_9r2_1)
  (princ "\n Исходные данные: ")
  (princ "\nd1                 = ")
  (princ (* r1 2.))
  (princ "\nd2                 = ")
  (princ (* r2 2.))
  (princ "\nr1                 = ")
  (princ r_1)
  (princ "\nl1                 = ")
  (princ l1)
  (princ "\nl2                 = ")
  (princ l2)
  (princ "\nh                  = ")
  (princ h)
  (princ "\na1                 = ")
  (princ (* (/ 180. pi) a1))
  (princ "\na2                 = ")
  (princ (* (/ 180. pi) a2))
  (princ "\na3                 = ")
  (princ (* (/ 180. pi) a3))
  (princ "\n Результаты расчета: ")
  (setq p2_9r1_1 (inters p2_9r1 (polar p2_9r1 (+ pi2 (angle p2_7_1 p2_6_3)) h) p2_7_1 p2_6_3 nil))
  (princ "\nРасстояние у корня лопатки        = ")
  (princ (setq lk (distance p2_9r1 p2_9r1_1)))
  (princ " ед")
  (setq p2_9r2_1 (inters p2_9r2 (polar p2_9r2 (+ pi2 (angle p2_7_1 p2_6_3)) h) p2_7_1 p2_6_3 nil))
  (princ "\nРасстояние на периферии лопатки   = ")
  (princ (setq lp (distance p2_9r2 p2_9r2_1)))
  (princ " ед")
  (princ "\nВысота лопатки                    = ")
  (princ (setq hl (distance p1_1 p1_2)))
  (princ " ед")
  (princ "\nКоличество лопаток                = ")
  (princ n)
  (princ " шт.")
  (princ "\nПлощадь одного лопаточного проема = ")
  (princ (setq f1 (* (+ lp lk) 0.5 hl)))
  (princ " ед^2")
  (princ "\nПлощадь завихрителя               = ")
  (princ (setq f (* f1 n)))
  (princ " ед^2")
  (princ))
