;;;(princ "\nЗагружаю Lopatka/Lopatka     ")
(princ (strcat "\nЗагружаю " (acad_sup) "/" "Lopatka/Lopatka     "))

;;;;;;("lo" "Построение профиля лопатки." "Расчеты")
(defun c:lo (/ str str1 temp ss1)
  (setq	old_err	*error*
	*error*	lo:my_err
  )
  (setvar "cmdecho" 0)
  (setq	str ""
	ss1 (ssadd)
  )
  (while (/= str "eXit")
    (initget "P1 P2 P3 D1 D2 H L1 L2 R1 A1 A2 A3 N Slide Redraw Draw Erase File eXit")
    (setq str1 (getkword
		 (strcat "\nP1 P2 P3 D1 D2 H L1 L2 R1 A1 A2 A3 N Slide Redraw Draw Erase File eXit <"
			 str
			 "> :"
		 )
	       )
    )
    (if	str1
      (setq str str1)
    )
    (cond
      ((= str "P1")
       (setq temp  p1_01
	     p1_01 nil
       )
       (while (null p1_01)
	 (if temp
	   (print temp)
	   (terpri)
	 )
	 (setq p1_01 (getpoint " p1_01 :"))
	 (if (null p1_01)
	   (setq p1_01 temp)
	 )
       )
      )
      ((= str "P2")
       (setq temp p2_0
	     p2_0 nil
       )
       (while (null p2_0)
	 (if temp
	   (print temp)
	   (terpri)
	 )
	 (setq p2_0 (getpoint " p2_0 :"))
	 (if (null p2_0)
	   (setq p2_0 temp)
	 )
       )
      )
      ((= str "P3")
       (setq temp p3_0
	     p3_0 nil
       )
       (while (null p3_0)
	 (if temp
	   (print temp)
	   (terpri)
	 )
	 (setq p3_0 (getpoint " p3 :"))
	 (if (null p3_0)
	   (setq p3_0 temp)
	 )
       )
      )
      ((= str "D1")
       (setq temp r1
	     r1	nil
       )
       (while (null r1)
	 (if temp
	   (print (* temp 2.))
	   (terpri)
	 )
	 (setq r1 (getdist " d1 :"))
	 (if (null r1)
	   (setq r1 temp)
	   (setq r1 (/ r1 2.))
	 )
       )
      )
      ((= str "D2")
       (setq temp r2
	     r2	nil
       )
       (while (null r2)
	 (if temp
	   (print (* temp 2.))
	   (terpri)
	 )
	 (setq r2 (getdist " d2 :"))
	 (if (null r2)
	   (setq r2 temp)
	   (setq r2 (/ r2 2.))
	 )
       )
      )
      ((= str "H")
       (setq temp h
	     h nil
       )
       (while (null h)
	 (if temp
	   (print temp)
	   (terpri)
	 )
	 (setq h (getdist " h :"))
	 (if (null h)
	   (setq h temp)
	 )
       )
      )
      ((= str "L1")
       (setq temp l1
	     l1	nil
       )
       (while (null l1)
	 (if temp
	   (print temp)
	   (terpri)
	 )
	 (setq l1 (getdist " l1 :"))
	 (if (null l1)
	   (setq l1 temp)
	 )
       )
      )
      ((= str "L2")
       (setq temp l2
	     l2	nil
       )
       (while (null l2)
	 (if temp
	   (print temp)
	   (terpri)
	 )
	 (setq l2 (getdist " l2 :"))
	 (if (null l2)
	   (setq l2 temp)
	 )
       )
      )
      ((= str "R1")
       (setq temp r_1
	     r_1  nil
       )
       (while (null r_1)
	 (if temp
	   (print temp)
	   (terpri)
	 )
	 (setq r_1 (getdist " r1 :"))
	 (if (null r_1)
	   (setq r_1 temp)
	 )
       )
      )
      ((= str "A1")
       (setq temp a1
	     a1	nil
       )
       (while (null a1)
	 (if temp
	   (print (* temp (/ 180. pi)))
	   (terpri)
	 )
	 (setq a1 (getangle " a1 :"))
	 (if (null a1)
	   (setq a1 temp)
	 )
       )
      )
      ((= str "A2")
       (setq temp a2
	     a2	nil
       )
       (while (null a2)
	 (if temp
	   (print (* temp (/ 180. pi)))
	   (terpri)
	 )
	 (setq a2 (getangle " a2 :"))
	 (if (null a2)
	   (setq a2 temp)
	 )
       )
      )
      ((= str "A3")
       (setq temp a3
	     a3	nil
       )
       (while (null a3)
	 (if temp
	   (print (* temp (/ 180. pi)))
	   (terpri)
	 )
	 (setq a3 (getangle " a3 :"))
	 (if (null a3)
	   (setq a3 temp)
	 )
       )
      )
      ((= str "N")
       (setq temp n
	     n nil
       )
       (while (null n)
	 (if temp
	   (print temp)
	   (terpri)
	 )
	 (setq n (getint " n :"))
	 (if (null n)
	   (setq n temp)
	 )
       )
      )
      ((= str "Slide")
       (command "_.vslide" "lopatka\\lopatka")
      )
      ((= str "File")
       (lo:lop_7)
      )
      ((= str "Redraw")
       (command "_.redraw")
      )
      ((= str "Erase")
       (if (> (sslength ss1) 0)
	 (command "_.erase" ss1 "")
       )
      )
      ((= str "Draw")
       (if (> (sslength ss1) 0)
	 (command "_.erase" ss1 "")
       )
       (setq en1 (entlast))
       (if (and p1_01 p2_0 p3_0 r1 r2 h l1 l2 r_1 a1 a2 a3 n)
	 (progn
	   (setq data t)
	   (lo:draw_lop)
	 )
	 (progn
	   (print "Не все данные введены !")
	   (setq data nil)
	 )
       )
       (setq ss1 (ssadd))
       (while (setq en1 (entnext en1))
	 (setq ss1 (ssadd en1 ss1))
       )
      )
    )
  )
  (command "_.redraw")
  (setq *error* old_err)
  (setvar "cmdecho" 1)
  (princ)
)

(princ "\t...загружен.\n")
 ;|«Visual LISP© Format Options»
(105 2 15 2 nil "end of" 90 15 0 0 0 T T nil T)
;*** DO NOT add text below the comment! ***|;
