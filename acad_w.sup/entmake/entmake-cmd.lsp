;;;;;;("ems"
;;;;;;"Сохранение объектов во внешнем dat файле в формате, выводимом командой entmake." "Обмен")
(defun c:ems  (/ li ss1 ff1 k tmp fn)
  (princ "Сохранение примитивов в файле в формате entmake.")
  (setq ss1 (ssget))
  (repeat (setq k (sslength ss1))
    (setq k   (1- k)
          tmp nil)
    (mapcar (function (lambda (el / cod)
                        (setq cod (car el))
                        (cond ((or (= cod -1) (= cod 5) (= cod 330)))
                              (t (setq tmp (cons el tmp))))))
            (entget (ssname ss1 k)))
    (setq li (cons (reverse tmp) li)))
  (setq fn  (getfiled "Имя файла для сохранения примитивов" "defautl" "dat" 1)
        ff1 (open fn "w"))
  (if (null ff1)
    (progn (file-open-err fn))
    (progn (princ "(setq li '" ff1) (prin1 li ff1) (princ ")\n" ff1) (close ff1)))
  (princ))

;;;;;;("eml"
;;;;;;"Вставка объектов, хранящихся в dat файле в формате entmake." "Обмен")
(defun c:eml  (/ li fn)
  (princ "Отрисовка примитивов хранящихся в файле в формате entmake.")
  (setq fn (getfiled "Имя файла для сохранения примитивов" "defautl" "dat" 0))
  (load fn)
  (mapcar 'entmake li)
  (princ))
