(setq scale_mult '(1.0 1.25 1.600 2.0 2.5 3.2000 4.00 5.0 6.25 8.000 10.)
      scale_dev  '(1.0 0.80 0.625 0.5 0.4 0.3125 0.25 0.2 0.16 0.125 0.1))

;;;;;;("te+" "Добавляет круглые скобки вокруг текста размерного примитива." "Тексты")
(defun c:te+  (/ en ed txt-str ss ss_td i)
  (err-init '("cmdecho"))
  (set-sys-var-lst '(("cmdecho" 0)))
  (prompt "\nВыберите тексты или размеры :")
  (setq ss (ssget '((-4 . "<OR") (0 . "DIMENSION") (0 . "TEXT") (0 . "MTEXT") (-4 . "OR>")))
        i  (sslength ss))
  (while (>= (setq i (1- i)) 0)
    (setq en  (ssname ss i)
          ed  (entget en)
          txt-str (cdr (assoc 1 ed)))
    (cond ((= txt-str "") (setq txt-str "(<>)"))
          ((= txt-str "<>") (setq txt-str "(<>)"))
          (t (setq txt-str (strcat "(" txt-str ")"))))
    (setq ed (subst (cons 1 txt-str) (assoc 1 ed) ed))
    (entmod ed))
  (err-handle ""))

;;;;;;("te+" "Добавляет круглые скобки увеличенного размера вокруг текста размерного примитива." "Тексты")
(defun c:te++  (/ en ed txt-str ss ss_td i)
  (err-init '("cmdecho"))
  (set-sys-var-lst '(("cmdecho" 0)))
  (prompt "\nВыберите тексты или размеры :")
  (setq ss (ssget '((-4 . "<OR") (0 . "DIMENSION") (0 . "TEXT") (0 . "MTEXT") (-4 . "OR>")))
        i  (sslength ss))
  (while (>= (setq i (1- i)) 0)
    (setq en  (ssname ss i)
          ed  (entget en)
          txt-str (cdr (assoc 1 ed)))
    (cond ((= txt-str "") (setq txt-str "{\\H2x(\\H0.5x}<>{\\H2x)\\H0.5x}"))
          ((= txt-str "<>") (setq txt-str "{\\H2x(\\H0.5x}<>{\\H2x)\\H0.5x}"))
          (t (setq txt-str (strcat "{\\H2x(\\H0.5x}" txt-str "{\\H2x)\\H0.5x}"))))
    (setq ed (subst (cons 1 txt-str) (assoc 1 ed) ed))
    (entmod ed))
  (err-handle ""))


;;;;;;("te+kvsk" "Добавляет квадратные скобки вокруг текста размерного примитива." "Тексты")
(defun c:te+kvsk  (/ en ed txt-str ss ss_td i)
  (err-init '("cmdecho"))
  (set-sys-var-lst '(("cmdecho" 0)))
  (prompt "\nВыберите тексты или размеры :")
  (setq ss (ssget '((-4 . "<OR") (0 . "DIMENSION") (0 . "TEXT") (0 . "MTEXT") (-4 . "OR>")))
        i  (sslength ss))
  (while (>= (setq i (1- i)) 0)
    (setq en  (ssname ss i)
          ed  (entget en)
          txt-str (cdr (assoc 1 ed)))
    (cond ((or (= txt-str "") (= txt-str "<>")) (setq txt-str "[<>]"))
          (t (setq txt-str (strcat "[" txt-str "]"))))
    (setq ed (subst (cons 1 txt-str) (assoc 1 ed) ed))
    (entmod ed))
  (err-handle ""))

;;;;;;("te++kvsk" "Добавляет квадратные скобки увеличенного размера вокруг текста размерного примитива." "Тексты")
(defun c:te++kvsk  (/ en ed txt-str ss ss_td i)
  (err-init '("cmdecho"))
  (set-sys-var-lst '(("cmdecho" 0)))
  (prompt "\nВыберите тексты или размеры :")
  (setq ss (ssget '((-4 . "<OR") (0 . "DIMENSION") (0 . "TEXT") (0 . "MTEXT") (-4 . "OR>")))
        i  (sslength ss))
  (while (>= (setq i (1- i)) 0)
    (setq en  (ssname ss i)
          ed  (entget en)
          txt-str (cdr (assoc 1 ed)))
    (cond ((= txt-str "") (setq txt-str "{\\H2x[\\H0.5x}<>{\\H2x]\\H0.5x}"))
          ((= txt-str "<>") (setq txt-str "{\\H2x[\\H0.5x}<>{\\H2x]\\H0.5x}"))
          (t (setq txt-str (strcat "{\\H2x[\\H0.5x}" txt-str "{\\H2x]\\H0.5x}"))))
    (setq ed (subst (cons 1 txt-str) (assoc 1 ed) ed))
    (entmod ed))
  (err-handle ""))


;;;;;;("te-" "Удаляет круглые скобки, находившиеся вокруг текста размерного примитива." "Тексты")
(defun c:te-  (/ ed en i sk_close sk_open ss txt-str str_1 str_2 str_3)
  (err-init '("cmdecho"))
  (set-sys-var-lst '(("cmdecho" 0)))
  (prompt "\nВыберите размеры :")
  (setq ss (ssget '((-4 . "<OR") (0 . "DIMENSION") (0 . "TEXT") (0 . "MTEXT") (-4 . "OR>")))
        i  (sslength ss))
  (while (>= (setq i (1- i)) 0)
    (setq en  (ssname ss i)
          ed  (entget en)
          txt-str (cdr (assoc 1 ed)))
    (setq sk_open  (vl-string-position (ascii "(") txt-str)
          sk_close (vl-string-position (ascii ")") txt-str nil t))
    (if (and (and sk_open sk_close) (< sk_open sk_close))
      (setq str_1 (substr txt-str 1 sk_open)
            str_2 (substr txt-str (+ 2 sk_open) (- sk_close sk_open 1))
            str_3 (substr txt-str (+ 2 sk_close))
            txt-str   (strcat str_1 str_2 str_3)))
    (setq txt-str (string-subst-all "" "{\\H2x\\H0.5x}" txt-str))
    (setq txt-str (strcat "\\A1;" (string-subst-all "" "\\A1;" txt-str)))
    (setq ed (subst (cons 1 txt-str) (assoc 1 ed) ed))
    (entmod ed))
  (err-handle ""))



;;;;;;("te-kvsk" "Удаляет квадратные скобки, находившиеся вокруг текста размерного примитива." "Тексты")
(defun c:te-kvsk  (/ ed en i sk_close sk_open ss txt-str str_1 str_2 str_3)
  (err-init '("cmdecho"))
  (set-sys-var-lst '(("cmdecho" 0)))
  (prompt "\nВыберите размеры :")
  (setq ss (ssget '((-4 . "<OR") (0 . "DIMENSION") (0 . "TEXT") (0 . "MTEXT") (-4 . "OR>")))
        i  (sslength ss))
  (while (>= (setq i (1- i)) 0)
    (setq en  (ssname ss i)
          ed  (entget en)
          txt-str (cdr (assoc 1 ed)))
    (setq sk_open  (vl-string-position (ascii "[") txt-str)
          sk_close (vl-string-position (ascii "]") txt-str nil t))
    (if (and (and sk_open sk_close) (< sk_open sk_close))
      (setq str_1 (substr txt-str 1 sk_open)
            str_2 (substr txt-str (+ 2 sk_open) (- sk_close sk_open 1))
            str_3 (substr txt-str (+ 2 sk_close))
            txt-str   (strcat str_1 str_2 str_3)))
    (setq txt-str (string-subst-all "" "{\\H2x\\H0.5x}" txt-str))
    (setq txt-str (strcat "\\A1;" (string-subst-all "" "\\A1;" txt-str)))
    (setq ed (subst (cons 1 txt-str) (assoc 1 ed) ed))
    (entmod ed))
  (err-handle ""))


;;;;;;("te%%c" "Добавляет знак диаметра перед текстом размерного примитива." "Тексты")
(defun c:te%%c  (/ en ed txt-str ss ss_td i)
  (err-init '("cmdecho"))
  (set-sys-var-lst '(("cmdecho" 0)))
  (prompt "\nВыберите размеры :")
  (setq ss (ssget '((-4 . "<OR") (0 . "DIMENSION") (0 . "TEXT") (0 . "MTEXT") (-4 . "OR>")))
        i  (sslength ss))
  (while (>= (setq i (1- i)) 0)
    (setq en  (ssname ss i)
          ed  (entget en)
          txt-str (cdr (assoc 1 ed)))
    (cond ((or (= txt-str "") (= txt-str "<>")) (setq txt-str "%%C<>"))
          (t (setq txt-str (vl-string-subst "%%C<>" "<>" txt-str))))
    (setq ed (subst (cons 1 txt-str) (assoc 1 ed) ed))
    (entmod ed))
  (err-handle ""))

;;;;;;("te-%%c" "Удаляет знак диаметра, находившийся перед текстом размерного примитива." "Тексты")
(defun c:te-%%c  (/ en ed txt-str ss ss_td i)
  (err-init '("cmdecho"))
  (set-sys-var-lst '(("cmdecho" 0)))
  (prompt "\nВыберите размеры :")
  (setq ss (ssget '((-4 . "<OR") (0 . "DIMENSION") (0 . "TEXT") (0 . "MTEXT") (-4 . "OR>")))
        i  (sslength ss))
  (while (>= (setq i (1- i)) 0)
    (setq en  (ssname ss i)
          ed  (entget en)
          txt-str (cdr (assoc 1 ed)))
    (cond ((= txt-str "%%C<>") (setq txt-str ""))
          (t (setq txt-str (vl-string-subst "<>" "%%C<>" txt-str))))
    (setq ed (subst (cons 1 txt-str) (assoc 1 ed) ed))
    (entmod ed))
  (err-handle ""))

;;;;;;("x45%%d" "Добавляет знак \"на 45 градусов\" после текста размерного примитива." "Тексты")
(defun c:x45%%d  (/ en ed txt-str ss ss_td i)
  (err-init '("cmdecho"))
  (set-sys-var-lst '(("cmdecho" 0)))
  (prompt "\nВыберите тексты или размеры :")
  (setq ss (ssget '((-4 . "<OR") (0 . "DIMENSION") (0 . "TEXT") (0 . "MTEXT") (-4 . "OR>")))
        i  (sslength ss))
  (while (>= (setq i (1- i)) 0)
    (setq en  (ssname ss i)
          ed  (entget en)
          txt-str (cdr (assoc 1 ed)))
    (cond ((= txt-str "") (setq txt-str "<>&L45%%d"))
          ((= txt-str "<>") (setq txt-str "<>&L45%%d"))
          (t (setq txt-str (strcat txt-str "&L45%%d"))))
    (setq ed (subst (cons 1 txt-str) (assoc 1 ed) ed))
    (entmod ed))
  (err-handle ""))


;;;;;;("&A&B&C" "Добавляет к тексту размерного примитива обозначение предельных отклонений." "Тексты")
(defun c:&a&b&c  (/ en ed txt-str ss ss_td i)
  (err-init '("cmdecho"))
  (set-sys-var-lst '(("cmdecho" 0)))
  (prompt "\nВыберите тексты или размеры :")
  (setq ss (ssget '((-4 . "<OR") (0 . "DIMENSION") (0 . "TEXT") (0 . "MTEXT") (-4 . "OR>")))
        i  (sslength ss))               ;setq
  (while (>= (setq i (1- i)) 0)
    (setq en  (ssname ss i)
          ed  (entget en)
          txt-str (cdr (assoc 1 ed)))
    (cond ((or (= txt-str "") (= txt-str "<>")) (setq txt-str "\\A1;<>{\\H0.725x;\\S+0.03^-0.06;}"))
          (t (setq txt-str (strcat "\\A1;" txt-str "{\\H0.725x;\\S+0.025^-0.001;}"))))
    (setq ed (subst (cons 1 txt-str) (assoc 1 ed) ed))
    (entmod ed))
  (err-handle ""))

;;;;;;("te_*" "Добавляет к тексту размерного примитива значок звездочка." "Тексты")
(defun c:te_*  (/ en ed txt-str ss ss_td i)
  (err-init '("cmdecho"))
  (set-sys-var-lst '(("cmdecho" 0)))
  (prompt "\nВыберите тексты или размеры :")
  (setq ss (ssget '((-4 . "<OR") (0 . "DIMENSION") (0 . "TEXT") (0 . "MTEXT") (-4 . "OR>")))
        i  (sslength ss))               ;setq
  (while (>= (setq i (1- i)) 0)
    (setq en  (ssname ss i)
          ed  (entget en)
          txt-str (cdr (assoc 1 ed)))
    (cond ((or (= txt-str "") (= txt-str "<>")) (setq txt-str "<>\\A1;{\\S*^;}"))
          (t (setq txt-str (strcat txt-str "\\A1;{\\S*^;}"))))
    (setq ed (subst (cons 1 txt-str) (assoc 1 ed) ed))
    (entmod ed))
  (err-handle ""))

;;;;;;("te_<>_" "Добавляет для неразрывные пробелы вокруг текста размера." "Тексты")
(defun c:te_<>_  (/ en ed txt-str ss ss_td i)
  (err-init '("cmdecho"))
  (set-sys-var-lst '(("cmdecho" 0)))
  (prompt "\nВыберите тексты или размеры :")
  (setq ss (ssget '((-4 . "<OR") (0 . "DIMENSION") (0 . "TEXT") (0 . "MTEXT") (-4 . "OR>")))
        i  (sslength ss))
  (while (>= (setq i (1- i)) 0)
    (setq en  (ssname ss i)
          ed  (entget en)
          txt-str (cdr (assoc 1 ed)))
    (cond ((or (= txt-str "") (= txt-str "<>")) (setq txt-str "\\~\\~\\~<>\\~\\~\\~"))
          (t (setq txt-str (strcat "\\~\\~\\~" txt-str "\\~\\~\\~"))))
    (setq ed (subst (cons 1 txt-str) (assoc 1 ed) ed))
    (entmod ed))
  (err-handle ""))
