;;;;;;("text_extract" "not defined" "Тексты")
(defun c:text_extract (/ fd fn i name ss txt)
  (setq	fn (getfiled "" "" "txt" 1)
	fd (open fn "W")
  )
  (cond
    ((/= 'str (type fn))
     (alert (princ "Переменная fn не содержит имени файла."))     
    )
    ((null fd)
     (alert(princ(strcat "Не могу открыть файл: " fn ".")))
     (exit)
    )
  )

  (setq	ss (ssget '((0 . "TEXT")))
	i  (sslength ss)
  )
  (while (>= (setq i (1- i)) 0)
    (setq name (ssname ss i)
	  txt
	       (cdr (assoc 1 (entget name)))
    )
    (princ txt fd)
    (princ "\n" fd)
  )
  (close fd)
)
