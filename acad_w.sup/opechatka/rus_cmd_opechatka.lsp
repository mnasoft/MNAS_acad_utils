(setq str_keyboard
       "zZxXcCvVbBnNmM,<.>/?`~qQwWeErRtTyYuUiIoOpP[{]}aAsSdDfFgGhHjJkKlL;:'\"ÿß÷×ñÑìÌèÈòÒüÜáÁþÞ.,¸¨éÉöÖóÓêÊåÅíÍãÃøØùÙçÇõÕúÚôÔûÛâÂàÀïÏðÐîÎëËäÄæÆýÝ")
(setq str_opchatka
       "ÿß÷×ñÑìÌèÈòÒüÜáÁþÞ.,¸¨éÉöÖóÓêÊåÅíÍãÃøØùÙçÇõÕúÚôÔûÛâÂàÀïÏðÐîÎëËäÄæÆýÝzZxXcCvVbBnNmM,<.>/?`~qQwWeErRtTyYuUiIoOpP[{]}aAsSdDfFgGhHjJkKlL;:'\"")

;;; Ïðîèçâîäèò äëÿ ñïèñêà l_cmds, ñîñòîÿùåãî èç ñòðîê èõ òðàíñëÿöèþ â äðóãóþ êîäèðîâêó.
;;;_$ (l_op_str '("str" "l" "àøä"))
;;;("ûåê" "ä" "fil")
(defun l_op_str  (l_cmds / rez el)
  (foreach el l_cmds (setq rez (cons (vl-string-translate str_keyboard str_opchatka el) rez)) (reverse rez)))

;;; Ïðîèçâîäèò òðàíñëÿöèþ ñïèñêà, l_cmds â äóãóþ êîäèðîâêó è çàãðóæàåò èõ â ïàìÿòü.
(defun opech_cmds-str  (l_cmds / op_cmds)
  (setq op_cmds (l_op_str l_cmds))
  (mapcar (function (lambda (cmd op)
                      (setq cmd (strcat "c:" cmd)
                            op  (strcat "c:" op))
                      (princ (strcat "\n(defun " op "() (" cmd "))"))))
          l_cmds
          op_cmds)
  (princ))
